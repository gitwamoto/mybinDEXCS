#!/usr/bin/env python
# -*- coding: utf-8 -*-
# exportStl.FCMacro
# by Yukiharu Iwamoto
# 2026/7/23 9:55:21 AM

import os
import sys
from PySide import QtGui
import tempfile
import Mesh

def exportStl(freecad_objects, file_path):
    tmp_stl = tempfile.mkstemp(suffix = '.ast')[1]
    with open(file_path, 'w') as f:
        for obj in freecad_objects:
            try:
                if obj.ViewObject.Visibility and hasattr(obj, 'Shape') and not hasattr(obj, 'ResizeMode'):
                    # DatumPlane has an attribute of 'ResizeMode'
                    Mesh.export([obj], tmp_stl)
                    for line in open(tmp_stl, 'r'):
                        if 'endsolid' in line:
                            f.write(f'endsolid {obj.Label}\n')
                        elif 'solid' in line:
                            f.write(f'solid {obj.Label}\n')
                        else:
                            f.write(line)
                    os.remove(tmp_stl)
            except:
#                print(sys.exc_info())
                pass

if __name__ == '__main__':
    doc = App.ActiveDocument
    file_path = os.path.splitext(QtGui.QFileDialog.getSaveFileName(None,
        'Save as STL file', f'{os.path.dirname(doc.FileName))[0])[0]}.stl'
    if file_path != '.stl':
        exportStl(doc.Objects, file_path)
        QtGui.QMessageBox.information(None, 'Exported', f'{file_path} is exported.')
