#!/usr/bin/env python
# -*- coding: utf-8 -*-
# makeSnappyHexMeshSetting.FCMacro
# by Yukiharu Iwamoto
# 2026/10/23 1:25:08 PM

VERSION = "2026/10/23 1:25:08 PM"

from PySide import QtCore, QtGui
from functools import partial
import os
import shutil
import tempfile
import Mesh
import re
import sys
import subprocess

binDEXCS_path = os.path.expanduser(
    "~/Desktop/binDEXCS（解析フォルダを端末で開いてから）"
)  # dakuten.py -j -f <path> で濁点を結合しておく
if binDEXCS_path not in sys.path:
    sys.path.append(binDEXCS_path)
from utilities import dictParse


class FreeCadFileGrid(QtGui.QTableWidget):
    OBJECT_NAME = 0
    TYPE = 1
    LEVEL = 2
    BOUNDARY_LAYER = 3
    N_LAYERS = 4
    RATIO = 5

    COL_LABELS = [
        "OjbectName",
        "Type",
        "Refinement\nLevel",
        "Boundary\nLayer",
        "nLayers",
        "Ratio/Thickness\nfor SurfaceRefine",
    ]

    def __init__(self, parent, freecad_objects):
        super(FreeCadFileGrid, self).__init__(parent)
        pat = re.compile(
            r"[\x20-\x7E]+$"
        )  # 半角の英数字と標準的な半角記号（ASCII範囲内）のみ許可する正規表現
        self.table = []
        for obj in freecad_objects:
            try:
                if (
                    obj.ViewObject.Visibility
                    and hasattr(obj, "Shape")
                    and "PartDesign::"
                    not in obj.TypeId  # Bodyや押し出しなどのフィーチャーを排除
                    and not hasattr(obj, "Role")  # 軸や原点を排除
                ):
                    if pat.match(obj.Label) is None:
                        QtGui.QMessageBox.critical(
                            None,
                            "動作保証外",
                            f"ラベル{obj.Label}が全角文字を含んでいます．\n"
                            "動作が保証できません．半角文字で名前をつけ直して下さい．",
                            QtGui.QMessageBox.Close,
                        )
                        raise ValueError("zenkaku label")
                    self.table.append([obj.Label, None, 0, False, 2, 1.2])
            except ValueError:
                raise
            except Exception:
                print(sys.exc_info())
        self.setRowCount(len(self.table))
        self.setColumnCount(len(self.table[0]))
        self.setHorizontalHeaderLabels(FreeCadFileGrid.COL_LABELS)
        self.horizontalHeader().setResizeMode(QtGui.QHeaderView.ResizeToContents)
        self.horizontalHeader().setResizeMode(
            FreeCadFileGrid.OBJECT_NAME, QtGui.QHeaderView.Stretch
        )
        for i in range(self.rowCount()):
            item = QtGui.QTableWidgetItem(
                str(self.table[i][FreeCadFileGrid.OBJECT_NAME])
            )
            item.setFlags(item.flags() & ~QtCore.Qt.ItemIsEditable)
            item.setTextAlignment(QtCore.Qt.AlignCenter)
            self.setItem(i, FreeCadFileGrid.OBJECT_NAME, item)
            for j in (
                FreeCadFileGrid.LEVEL,
                FreeCadFileGrid.N_LAYERS,
                FreeCadFileGrid.RATIO,
            ):
                item = QtGui.QTableWidgetItem(str(self.table[i][j]))
                item.setTextAlignment(QtCore.Qt.AlignRight)
                self.setItem(i, j, item)
            combo = QtGui.QComboBox()
            combo.addItems(
                [
                    "patch",
                    "wall",
                    "empty",
                    "symmetryPlane",
                    "symmetry",
                    "overset",
                    "BoxRefine",
                    "CylinderRefine",
                    "SphereRefine",
                    "SurfaceRefine",
                    "BoxSet",
                    "CylinderSet",
                    "SphereSet",
                    "BoxTopo",
                    "CylinderTopo",
                    "SphereTopo",
                    "LocationInMesh",
                    "N/A",
                ]
            )
            self.setCellWidget(i, FreeCadFileGrid.TYPE, combo)
            self.table[i][FreeCadFileGrid.TYPE] = combo.itemText(combo.currentIndex())
            combo.currentIndexChanged.connect(
                partial(self.actionOnCurrentIndexChanged, i)
            )
            check = QtGui.QCheckBox()
            self.setCellWidget(i, FreeCadFileGrid.BOUNDARY_LAYER, check)
            self.table[i][FreeCadFileGrid.BOUNDARY_LAYER] = check.isChecked()
            check.stateChanged.connect(partial(self.actionOnStateChanged, i))
        self.cellChanged.connect(self.actionOnCellChanged)

    def actionOnCurrentIndexChanged(self, row, index):
        self.updateTable(
            row,
            FreeCadFileGrid.TYPE,
            self.cellWidget(row, FreeCadFileGrid.TYPE).itemText(index),
        )

    def actionOnStateChanged(self, row, state):
        try:
            self.updateTable(
                row, FreeCadFileGrid.BOUNDARY_LAYER, state == QtCore.Qt.Checked.value
            )
        except Exception:
            self.updateTable(
                row, FreeCadFileGrid.BOUNDARY_LAYER, state == QtCore.Qt.Checked
            )

    def actionOnCellChanged(self, row, col):
        try:
            self.updateTable(row, col, self.item(row, col).text())
        except Exception:
            self.item(row, col).setText(str(self.table[row][col]))

    def updateTable(self, row, col, value):
        try:
            if col in (FreeCadFileGrid.LEVEL, FreeCadFileGrid.N_LAYERS):
                self.table[row][col] = int(value)
            elif col == FreeCadFileGrid.RATIO:
                self.table[row][col] = float(value)
            else:
                self.table[row][col] = value
        except Exception:
            raise

    def setCellValue(self, row, col, value):
        try:
            self.updateTable(row, col, value)
            if col == FreeCadFileGrid.TYPE:
                self.cellWidget(row, FreeCadFileGrid.TYPE).setCurrentIndex(
                    self.cellWidget(row, FreeCadFileGrid.TYPE).findText(value)
                )
            elif col == FreeCadFileGrid.BOUNDARY_LAYER:
                self.cellWidget(row, FreeCadFileGrid.BOUNDARY_LAYER).setCheckState(
                    QtCore.Qt.Checked if value else QtCore.Qt.Unchecked
                )
            else:
                self.item(row, col).setText(value)
        except Exception:
            pass


class MeshFrame(QtGui.QDialog):
    def __init__(
        self,
        controller,
        freecad_objects,
        case_dir_path,
        max_cell_size,
        features_level,
        feature_angle,
    ):
        if (
            re.match(r"[\x20-\x7E]+$", os.path.basename(case_dir_path)) is None
        ):  # 半角の英数字と標準的な半角記号（ASCII範囲内）のみ許可する正規表現
            QtGui.QMessageBox.critical(
                None,
                "動作保証外",
                f"解析フォルダ名{os.path.basename(case_dir_path)}が全角文字を含んでいます．\n"
                "動作が保証できません．半角文字で名前をつけ直して下さい．",
                QtGui.QMessageBox.Close,
            )
            raise ValueError("zenkaku path")

        super(MeshFrame, self).__init__(parent=None)
        self.setWindowTitle(
            f"snappyHexMesh settings from FreeCAD Model (.fcstd), {VERSION}"
        )

        self.controller = controller

        box_V = QtGui.QVBoxLayout()
        self.setLayout(box_V)

        box_H = QtGui.QHBoxLayout()
        box_V.addLayout(box_H)
        self.caseButton = QtGui.QPushButton("Case directory:")
        self.caseButton.setSizePolicy(QtGui.QSizePolicy.Fixed, QtGui.QSizePolicy.Fixed)
        self.caseButton.clicked.connect(self.controller.actionOnCaseButton)
        box_H.addWidget(self.caseButton)
        self.caseDirST = QtGui.QLabel(case_dir_path)
        box_H.addWidget(self.caseDirST)
        self.openButton = QtGui.QPushButton("xdg-open")
        self.openButton.setSizePolicy(QtGui.QSizePolicy.Fixed, QtGui.QSizePolicy.Fixed)
        self.openButton.clicked.connect(self.controller.actionOnOpenButton)
        box_H.addWidget(self.openButton)

        box_H = QtGui.QHBoxLayout()
        box_V.addLayout(box_H)
        box_H.addWidget(QtGui.QLabel("maxCellSize:"))
        self.maxCellSizeCRL = QtGui.QLineEdit(f"{max_cell_size:.2f}")
        self.maxCellSizeCRL.setAlignment(QtCore.Qt.AlignRight)
        self.maxCellSizeCRL.setValidator(QtGui.QDoubleValidator())
        box_H.addWidget(self.maxCellSizeCRL)
        box_H.addItem(QtGui.QSpacerItem(12, 0))
        box_H.addWidget(QtGui.QLabel("featuresLevel:"))
        self.featuresLevelCRL = QtGui.QLineEdit(f"{features_level}")
        self.featuresLevelCRL.setAlignment(QtCore.Qt.AlignRight)
        self.featuresLevelCRL.setValidator(QtGui.QIntValidator())
        box_H.addWidget(self.featuresLevelCRL)
        box_H.addItem(QtGui.QSpacerItem(12, 0))
        box_H.addWidget(QtGui.QLabel("featureAngle:"))
        self.featureAngleCRL = QtGui.QLineEdit(f"{feature_angle}")
        self.featureAngleCRL.setAlignment(QtCore.Qt.AlignRight)
        self.featureAngleCRL.setValidator(QtGui.QDoubleValidator())
        box_H.addWidget(self.featureAngleCRL)

        self.grid = FreeCadFileGrid(self, freecad_objects)
        box_V.addWidget(self.grid)
        box_V.addWidget(
            QtGui.QLabel(
                "※ 上の表は全ての可視オブジェクトを含んでいます.\n"
                "     可視性（Visibility）を切り替えるには，オブジェクトを選んだ後でスペースキーを押します．\n"
                "※ マルチリージョン解析の場合，LocationInMeshを複数作り，OjbectNameを領域名にして下さい．"
            )
        )

        box_H = QtGui.QHBoxLayout()
        box_V.addLayout(box_H)
        self.exportButton = QtGui.QPushButton("Export")
        self.exportButton.setSizePolicy(
            QtGui.QSizePolicy.Fixed, QtGui.QSizePolicy.Fixed
        )
        self.exportButton.clicked.connect(self.controller.actionOnExportButton)
        box_H.addWidget(self.exportButton)
        box_H.addWidget(QtGui.QLabel("->"))
        self.sHMeshButton = QtGui.QPushButton("snappyHexMesh")
        self.sHMeshButton.setSizePolicy(
            QtGui.QSizePolicy.Fixed, QtGui.QSizePolicy.Fixed
        )
        self.sHMeshButton.clicked.connect(self.controller.actionOnSHMeshButton)
        box_H.addWidget(self.sHMeshButton)
        box_H.addWidget(QtGui.QLabel("( ->"))
        self.improveMeshQualityButton = QtGui.QPushButton("improveMeshQuality")
        self.improveMeshQualityButton.setSizePolicy(
            QtGui.QSizePolicy.Fixed, QtGui.QSizePolicy.Fixed
        )
        self.improveMeshQualityButton.clicked.connect(
            self.controller.actionOnImproveMeshQualityButton
        )
        box_H.addWidget(self.improveMeshQualityButton)
        box_H.addWidget(QtGui.QLabel(","))
        self.flattenPatchButton = QtGui.QPushButton("Flatten patch")
        self.flattenPatchButton.setSizePolicy(
            QtGui.QSizePolicy.Fixed, QtGui.QSizePolicy.Fixed
        )
        self.flattenPatchButton.clicked.connect(
            self.controller.actionOnFlattenPatchButton
        )
        box_H.addWidget(self.flattenPatchButton)
        box_H.addWidget(QtGui.QLabel(","))
        self.extrudeMeshButton = QtGui.QPushButton("2D by extrudeMesh")
        self.extrudeMeshButton.setSizePolicy(
            QtGui.QSizePolicy.Fixed, QtGui.QSizePolicy.Fixed
        )
        self.extrudeMeshButton.clicked.connect(
            self.controller.actionOnExtrudeMeshButton
        )
        box_H.addWidget(self.extrudeMeshButton)
        box_H.addWidget(QtGui.QLabel(")"))
        box_H.addItem(
            QtGui.QSpacerItem(
                40, 20, QtGui.QSizePolicy.Expanding, QtGui.QSizePolicy.Minimum
            )
        )

        box_H = QtGui.QHBoxLayout()
        box_V.addLayout(box_H)
        self.loadButton = QtGui.QPushButton("Load")
        self.loadButton.setSizePolicy(QtGui.QSizePolicy.Fixed, QtGui.QSizePolicy.Fixed)
        self.loadButton.clicked.connect(self.controller.actionOnLoadButton)
        self.loadButton.setDefault(True)
        box_H.addWidget(self.loadButton)
        self.editButton = QtGui.QPushButton("Edit")
        self.editButton.setSizePolicy(QtGui.QSizePolicy.Fixed, QtGui.QSizePolicy.Fixed)
        self.editButton.clicked.connect(self.controller.actionOnEditButton)
        box_H.addWidget(self.editButton)
        box_H.addItem(
            QtGui.QSpacerItem(
                40, 20, QtGui.QSizePolicy.Expanding, QtGui.QSizePolicy.Minimum
            )
        )
        self.exitButton = QtGui.QPushButton("Exit")
        self.exitButton.setSizePolicy(QtGui.QSizePolicy.Fixed, QtGui.QSizePolicy.Fixed)
        self.exitButton.clicked.connect(self.actionOnExitButton)
        box_H.addWidget(self.exitButton)

    def setAllType(self, type_value):
        for i in range(self.grid.rowCount()):
            self.grid.setCellValue(i, self.grid.TYPE, type_value)

    def setParamsFromMeshDict(self, meshDict):
        if meshDict is None:
            return

        e = meshDict.find_element(
            [
                {"type": "block", "key": "CUSTOM_OPTIONS"},
                {"type": "dictionary", "key": "maxCellSize"},
                {"type": "float|integer"},
            ]
        )["element"]
        if e is not None:
            self.maxCellSizeCRL.setText(e["value"])

        castellatedMeshControls = meshDict.find_element(
            [{"type": "block", "key": "castellatedMeshControls"}]
        )["element"]

        e = castellatedMeshControls.find_element(
            [
                {"type": "dictionary", "key": "features"},
                {"type": "list"},
                {"type": "block"},
                {"type": "dictionary", "key": "level"},
                {"type": "integer"},
            ]
        )["element"]
        if e is not None:
            self.featuresLevelCRL.setText(e["value"])

        e = castellatedMeshControls.find_element(
            [
                {"type": "dictionary", "key": "resolveFeatureAngle"},
                {"type": "float|integer"},
            ]
        )["element"]
        if e is not None:
            self.featureAngleCRL.setText(e["value"])

        shape_name = None
        searchableBox_list = []
        searchableCylinder_list = []
        searchableSphere_list = []
        triSurface_list = []

        refinementSurfaces = castellatedMeshControls.find_element(
            [{"type": "block", "key": "refinementSurfaces"}]
        )["element"]

        for block in meshDict.find_all_elements(
            [{"type": "block", "key": "geometry"}, {"type": "block"}]
        ):
            block = block["element"]
            if block["key"].endswith(".stl"):
                name = block.find_element(
                    [{"type": "dictionary", "key": "name"}, {"type": "word"}]
                )["element"]["value"]
                if (
                    refinementSurfaces.find_element([{"type": "block", "key": name}])[
                        "element"
                    ]
                    is not None
                ):
                    shape_name = name
                else:
                    triSurface_list.append(name)
            else:
                v = block.find_element(
                    [{"type": "dictionary", "key": "type"}, {"type": "word"}]
                )["element"]["value"]
                if v in ("searchableBox", "searchableRotatedBox"):
                    searchableBox_list.append(block["key"])
                elif v == "searchableCylinder":
                    searchableCylinder_list.append(block["key"])
                elif v == "searchableSphere":
                    searchableSphere_list.append(block["key"])

        object_names = [i[self.grid.OBJECT_NAME] for i in self.grid.table]

        for block in refinementSurfaces.find_all_elements(
            [
                {"type": "block", "key": shape_name},
                {"type": "block", "key": "regions"},
                {"type": "block"},
            ]
        ):
            block = block["element"]
            if block["key"] in object_names:
                i = object_names.index(block["key"])
                e = block.find_element(
                    [
                        {"type": "dictionary", "key": "level"},
                        {"type": "list"},
                        {"type": "integer"},
                    ]
                )["element"]
                if e is not None:
                    self.grid.setCellValue(i, self.grid.LEVEL, e["value"])
                e = block.find_element(
                    [
                        {"type": "block", "key": "patchInfo"},
                        {"type": "dictionary", "key": "type"},
                        {"type": "word"},
                    ]
                )["element"]
                if e is not None:
                    self.grid.setCellValue(i, self.grid.TYPE, e["value"])

        for block in castellatedMeshControls.find_all_elements(
            [{"type": "block", "key": "refinementRegions"}, {"type": "block"}]
        ):
            block = block["element"]
            if block["key"] not in object_names or (
                block["key"] not in searchableBox_list
                and block["key"] not in searchableCylinder_list
                and block["key"] not in searchableSphere_list
                and block["key"] not in triSurface_list
            ):
                continue
            i = object_names.index(block["key"])
            if block["key"] in searchableBox_list:
                self.grid.setCellValue(i, self.grid.TYPE, "BoxRefine")
            elif block["key"] in searchableCylinder_list:
                self.grid.setCellValue(i, self.grid.TYPE, "CylinderRefine")
            elif block["key"] in searchableSphere_list:
                self.grid.setCellValue(i, self.grid.TYPE, "SphereRefine")
            else:
                self.grid.setCellValue(i, self.grid.TYPE, "SurfaceRefine")
            levels = block.find_element(
                [
                    {"type": "dictionary", "key": "levels"},
                    {"type": "list"},
                    {"type": "list"},
                ]
            )["element"]
            if levels is None:
                continue
            e = levels.find_element([{"type": "integer"}], reverse=True)[
                "element"
            ]  # level
            if e is not None:
                self.grid.setCellValue(i, self.grid.LEVEL, e["value"])
            if block["key"] in triSurface_list:
                e = levels.find_element([{"type": "float|integer"}])[
                    "element"
                ]  # distance
                if e is not None:
                    self.grid.setCellValue(i, self.grid.RATIO, e["value"])

        shape_prefix = f"{shape_name}_"
        len_shape_prefix = len(shape_prefix)
        for block in meshDict.find_all_elements(
            [
                {"type": "block", "key": "addLayersControls"},
                {"type": "block", "key": "layers"},
                {"type": "block"},
            ]
        ):
            block = block["element"]
            name = block["key"][len_shape_prefix:]
            if block["key"].startswith(shape_prefix) and name in object_names:
                i = object_names.index(name)
                e = block.find_element(
                    [
                        {"type": "dictionary", "key": "nSurfaceLayers"},
                        {"type": "integer"},
                    ]
                )["element"]
                if e is not None:
                    self.grid.setCellValue(i, self.grid.N_LAYERS, e["value"])
                    self.grid.setCellValue(i, self.grid.BOUNDARY_LAYER, True)
                e = block.find_element(
                    [
                        {"type": "dictionary", "key": "expansionRatio"},
                        {"type": "float|integer"},
                    ]
                )["element"]
                if e is not None:
                    self.grid.setCellValue(i, self.grid.RATIO, e["value"])

    def setParamsFromSetFieldsDict(self, setFieldsDict):
        if setFieldsDict is None:
            return

        object_names = [i[self.grid.OBJECT_NAME] for i in self.grid.table]
        for block in setFieldsDict.find_all_elements(
            [
                {"type": "dictionary", "key": "regions"},
                {"type": "list"},
                {"type": "block"},
            ],
            parent=setFieldsDict,
        ):
            block = block["element"]
            comment = block.find_element([{"type": "line_comment|block_comment"}])[
                "element"
            ]
            if comment is None or "freecad" not in comment["value"].lower():
                continue
            for i, obj in enumerate(object_names):
                if obj not in comment["value"]:
                    continue
                if block["key"] == "boxToCell":
                    self.grid.setCellValue(i, self.grid.TYPE, "BoxSet")
                elif block["key"] == "cylinderToCell":
                    self.grid.setCellValue(i, self.grid.TYPE, "CylinderSet")
                else:
                    self.grid.setCellValue(i, self.grid.TYPE, "SphereSet")

    def setParamsFromTopoSetDict(self, topoSetDict):
        if topoSetDict is None:
            return

        object_names = [i[self.grid.OBJECT_NAME] for i in self.grid.table]
        for block in topoSetDict.find_all_elements(
            [
                {"type": "dictionary", "key": "actions"},
                {"type": "list"},
                {"type": "block"},
            ]
        ):
            block = block["element"]
            v = (
                block.find_element(
                    [{"type": "dictionary", "key": "name"}, {"type": "word"}]
                )["element"]["value"]
                .replace("CellSet", "")
                .replace()
            )
            if v not in object_names:
                continue
            if (
                block.find_element(
                    [{"type": "dictionary", "key": "source"}, {"type": "word"}]
                )["element"]["value"]
                != "rotatedBoxToCell"
            ):
                continue
            self.grid.setCellValue(object_names.index(v), self.grid.TYPE, "BoxTopo")

    def actionOnExitButton(self):
        self.close()


class MyController:
    FEATURE_ANGLE = 30
    BASHRC_PATH_4_OPENFOAM = os.path.join(
        os.sep, "opt", "OpenFOAM", "OpenFOAM-v1906", "etc", "bashrc"
    )
    if not os.path.exists(BASHRC_PATH_4_OPENFOAM):
        BASHRC_PATH_4_OPENFOAM = os.path.join(
            os.sep, "usr", "lib", "openfoam", "openfoam2106", "etc", "bashrc"
        )
    SOLVER_PATH_TEMPLATE = os.path.join(os.sep, "opt", "DEXCS", "template", "dexcs")

    def __init__(self):
        import FreeCAD
        import Part

        self.doc = App.ActiveDocument
        self.model = MyModel()
        self.meshDict = None
        self.setFieldsDict = None
        self.topoSetDict = None
        if self.doc.FileName == "":
            QtGui.QMessageBox.critical(
                None,
                "エラー",
                "CADファイルが保存されていません．CADファイルを保存して下さい．",
                QtGui.QMessageBox.Close,
            )
            return
        for obj in self.doc.Objects:
            if (
                obj.ViewObject.Visibility
                and hasattr(obj, "Shape")
                and "PartDesign::"
                not in obj.TypeId  # Bodyや押し出しなどのフィーチャーを排除
                and not hasattr(obj, "Role")  # 軸や原点を排除
            ):
                obj.Label = obj.Label.strip()
                l = obj.Label
                obj.Label = re.sub("^([0-9])", r"_\1", l.replace(" ", "_"))
                if obj.Label != l:
                    QtGui.QMessageBox.warning(
                        None,
                        "オブジェクトラベル違反",
                        f"ラベル{l}を{obj.Label}に変更しました．",
                        QtGui.QMessageBox.Close,
                    )
        try:
            self.MeshFrame = MeshFrame(
                controller=self,
                freecad_objects=self.doc.Objects,
                case_dir_path=os.path.dirname(self.doc.FileName),  # 絶対パス
                max_cell_size=self.model.sumOfThreeEdgesOfCadObjects(self.doc.Objects)
                / 60.0,
                features_level=1,
                feature_angle=MyController.FEATURE_ANGLE,
            )
        except Exception:
            return
        self.MeshFrame.show()

    def actionOnCaseButton(self):
        dir_path = QtGui.QFileDialog.getExistingDirectory(
            self.MeshFrame,
            "Choose a directory.",
            os.path.expanduser(os.path.join("~", "Desktop")),
        )  # 絶対パス
        if dir_path != "":
            self.MeshFrame.caseDirST.setText(dir_path)

    def actionOnOpenButton(self):
        case_dir_path = self.MeshFrame.caseDirST.text()
        if os.path.isdir(case_dir_path):
            subprocess.run(["xdg-open", case_dir_path])

    def actionOnExportButton(self):
        if not os.path.isdir(self.MeshFrame.caseDirST.text()):
            QtGui.QMessageBox.critical(
                None,
                "エラー",
                f"{self.MeshFrame.caseDirST.text()}はフォルダではありません．",
                QtGui.QMessageBox.Close,
            )
            return
        num_of_LocationInMesh = sum(
            (
                1
                for i in self.MeshFrame.grid.table
                if i[self.MeshFrame.grid.TYPE] == "LocationInMesh"
            )
        )
        if num_of_LocationInMesh == 0:
            QtGui.QMessageBox.critical(
                None,
                "エラー",
                "LocationInMeshを指定して下さい．",
                QtGui.QMessageBox.Close,
            )
            return
        elif (
            num_of_LocationInMesh > 1
            and QtGui.QMessageBox.warning(
                None,
                "LocationInMesh",
                f"複数（{num_of_LocationInMesh}個）のLocationInMeshがあります．複数にするつもりですか？",
                QtGui.QMessageBox.Yes,
                QtGui.QMessageBox.No,
            )
            == QtGui.QMessageBox.No
        ):
            return  # chtMultiRegionFoam（共役熱伝導解析）ではLocationInMeshが複数ある
        case_dir_path = self.MeshFrame.caseDirST.text()  # 絶対パス
        # (DEXCS2019を参考に) OpenFOAMのケースフォルダでない場合の処理を追加（2019/9/6）
        if not os.path.isdir(os.path.join(case_dir_path, "constant")):
            subprocess.run(
                [
                    "rsync",
                    "-a",
                    os.path.join(MyController.SOLVER_PATH_TEMPLATE, "constant"),
                    case_dir_path,
                    "--exclude",
                    "polyMesh",
                ]
            )
        if not os.path.isdir(os.path.join(case_dir_path, "system")):
            shutil.copytree(
                os.path.join(MyController.SOLVER_PATH_TEMPLATE, "system"),
                os.path.join(case_dir_path, "system"),
            )
        if not os.path.isdir(os.path.join(case_dir_path, "0")):
            shutil.copytree(
                os.path.join(MyController.SOLVER_PATH_TEMPLATE, "0"),
                os.path.join(case_dir_path, "0"),
            )
        triSurface = os.path.join(case_dir_path, "constant", "triSurface")
        if os.path.isdir(triSurface):
            shutil.rmtree(triSurface)
        elif os.path.isfile(triSurface):
            os.remove(triSurface)
        os.mkdir(triSurface)
        extendedFeatureEdgeMesh = os.path.join(
            case_dir_path, "constant", "extendedFeatureEdgeMesh"
        )
        if os.path.isdir(extendedFeatureEdgeMesh):
            shutil.rmtree(extendedFeatureEdgeMesh)
        elif os.path.isfile(extendedFeatureEdgeMesh):
            os.remove(extendedFeatureEdgeMesh)
        stl_file_path = os.path.join(
            triSurface,
            re.sub("^([0-9])", r"_\1", f"{os.path.basename(case_dir_path)}.stl"),
        )
        box = self.model.exportStl(self.doc.Objects, self.MeshFrame.grid, stl_file_path)
        self.model.makeSurfaceFeatureExtractDict(  # 複数やった方が良い
            case_dir_path=case_dir_path,
            surface_file_path=stl_file_path,
            feature_angle=self.MeshFrame.featureAngleCRL.text(),
        )
        cwd = os.getcwd()
        os.chdir(case_dir_path)
        command = f". '{MyController.BASHRC_PATH_4_OPENFOAM}' && surfaceFeatureExtract"
        if subprocess.run(command, shell=True).returncode != 0:
            QtGui.QMessageBox.critical(
                None, "エラー", f"{command}が失敗しました．", QtGui.QMessageBox.Close
            )
            os.chdir(cwd)
            return
        os.chdir(cwd)
        self.model.makeMeshDict(
            case_dir_path=case_dir_path,
            surface_file_path=stl_file_path,
            max_cell_size=self.MeshFrame.maxCellSizeCRL.text(),
            bounding_box=box,
            freecad_objects=self.doc.Objects,
            grid=self.MeshFrame.grid,
            features_level=self.MeshFrame.featuresLevelCRL.text(),
            feature_angle=self.MeshFrame.featureAngleCRL.text(),
            meshDict=self.meshDict,
        )
        self.model.makeSetFieldsDict(
            case_dir_path=case_dir_path,
            freecad_objects=self.doc.Objects,
            grid=self.MeshFrame.grid,
            setFieldsDict=self.setFieldsDict,
        )
        self.model.makeTopoSetDict(
            case_dir_path=case_dir_path,
            freecad_objects=self.doc.Objects,
            grid=self.MeshFrame.grid,
            topoSetDict=self.topoSetDict,
        )
        QtGui.QMessageBox.information(
            None,
            "書き出し",
            "snappyHexMeshの設定ファイルsystem/snappyHexMeshDictを書き出しました．",
            QtGui.QMessageBox.Close,
        )

    def actionOnSHMeshButton(self):
        case_dir_path = self.MeshFrame.caseDirST.text()
        if (
            QtGui.QMessageBox.question(
                None,
                "snappyHexMesh",
                "メッシュ生成コマンドsnappyHexMeshを実行しますか？",
                QtGui.QMessageBox.Yes,
                QtGui.QMessageBox.No,
            )
            == QtGui.QMessageBox.Yes
        ):
            cwd = os.getcwd()
            os.chdir(case_dir_path)
            subprocess.run(
                [
                    "gnome-terminal",
                    "--",
                    "bash",
                    "-c",
                    f". '{MyController.BASHRC_PATH_4_OPENFOAM}' && "
                    f"'{os.path.join(binDEXCS_path, 'snappyHexMeshを実行.py')}'; exec bash",
                ]
            )
            # exec bashで画面が消えなくなる
            os.chdir(cwd)

    def actionOnExtrudeMeshButton(self):
        if (
            QtGui.QMessageBox.question(
                None,
                "2D by extrudeMesh",
                "2次元メッシュ作成コマンドextrudeMeshを実行しますか？",
                QtGui.QMessageBox.Yes,
                QtGui.QMessageBox.No,
            )
            == QtGui.QMessageBox.Yes
        ):
            cwd = os.getcwd()
            os.chdir(self.MeshFrame.caseDirST.text())
            subprocess.run(
                [
                    "gnome-terminal",
                    "--",
                    "bash",
                    "-c",
                    f". '{MyController.BASHRC_PATH_4_OPENFOAM}' && "
                    f"'{os.path.join(binDEXCS_path, '2次元メッシュに.py')}'; exec bash",
                ]
            )
            # exec bashで画面が消えなくなる
            os.chdir(cwd)

    def actionOnImproveMeshQualityButton(self):
        if (
            QtGui.QMessageBox.question(
                None,
                "improveMeshQuality",
                "メッシュ品質改良コマンドimproveMeshQualityを実行しますか？",
                QtGui.QMessageBox.Yes,
                QtGui.QMessageBox.No,
            )
            == QtGui.QMessageBox.Yes
        ):
            cwd = os.getcwd()
            os.chdir(self.MeshFrame.caseDirST.text())
            subprocess.run(
                [
                    "gnome-terminal",
                    "--",
                    "bash",
                    "-c",
                    f". '{MyController.BASHRC_PATH_4_OPENFOAM}' && "
                    f"'{os.path.join(binDEXCS_path, 'improveMeshQualityを実行.py')}'; exec bash",
                ]
            )
            # exec bashで画面が消えなくなる
            os.chdir(cwd)

    def actionOnFlattenPatchButton(self):
        if (
            QtGui.QMessageBox.question(
                None,
                "Flatten patch",
                "パッチを平面にしますか？",
                QtGui.QMessageBox.Yes,
                QtGui.QMessageBox.No,
            )
            == QtGui.QMessageBox.Yes
        ):
            cwd = os.getcwd()
            os.chdir(self.MeshFrame.caseDirST.text())
            subprocess.run(
                [
                    "gnome-terminal",
                    "--",
                    "bash",
                    "-c",
                    f". '{MyController.BASHRC_PATH_4_OPENFOAM}' && "
                    f"'{os.path.join(binDEXCS_path, 'patchを平面に.py')}'; exec bash",
                ]
            )
            # exec bashで画面が消えなくなる
            os.chdir(cwd)

    def actionOnLoadButton(self):
        case_dir_path = self.MeshFrame.caseDirST.text()  # 絶対パス
        if not os.path.isdir(case_dir_path):
            return

        def dictParser(dict_path):
            if not os.path.isfile(dict_path):
                return None
            d = dictParse.DictParser(file_name=dict_path)
            name = os.path.basename(dict_path)
            if (
                d.find_element(
                    [
                        {"type": "block", "key": "FoamFile"},
                        {"type": "dictionary", "key": "object"},
                        {"type": "word", "value": name},
                    ]
                )["element"]
                is None
            ):
                QtGui.QMessageBox.critical(
                    None,
                    "Error",
                    f"{d.file_name} is not a {name} file.",
                    QtGui.QMessageBox.Close,
                )
                return None
            return d

        self.MeshFrame.setAllType("LocationInMesh")

        self.meshDict = dictParser(
            os.path.join(case_dir_path, "system", "snappyHexMeshDict")
        )
        self.MeshFrame.setParamsFromMeshDict(self.meshDict)

        self.setFieldsDict = dictParser(
            os.path.join(case_dir_path, "system", "setFieldsDict")
        )
        self.MeshFrame.setParamsFromSetFieldsDict(self.setFieldsDict)

        self.topoSetDict = dictParser(
            os.path.join(case_dir_path, "system", "topoSetDict")
        )
        self.MeshFrame.setParamsFromTopoSetDict(self.topoSetDict)

        QtGui.QMessageBox.warning(
            None,
            "LocationInMesh",
            "LocationInMeshが正しく指定されているかを確認して下さい．",
            QtGui.QMessageBox.Close,
        )

    def actionOnEditButton(self):
        meshDict_path = os.path.join(
            self.MeshFrame.caseDirST.text(), "system", "snappyHexMeshDict"
        )
        if not os.path.isfile(meshDict_path):
            QtGui.QMessageBox.critical(
                None,
                "ファイルエラー",
                "system/snappyHexMeshDictファイルがありません，",
                QtGui.QMessageBox.Close,
            )
            return
        if (
            QtGui.QMessageBox.question(
                None,
                "編集",
                "system/snappyHexMeshDictファイルを編集しますか？\n",
                QtGui.QMessageBox.Yes,
                QtGui.QMessageBox.No,
            )
            == QtGui.QMessageBox.Yes
        ):
            subprocess.run(["gedit", meshDict_path])


class MyModel:
    @staticmethod
    def sumOfThreeEdgesOfCadObjects(freecad_objects):
        xmin = ymin = zmin = float("inf")
        xmax = ymax = zmax = float("-inf")
        for obj in freecad_objects:
            try:
                if (
                    obj.ViewObject.Visibility
                    and hasattr(obj, "Shape")
                    and "PartDesign::"
                    not in obj.TypeId  # Bodyや押し出しなどのフィーチャーを排除
                    and not hasattr(obj, "Role")  # 軸や原点を排除
                ):
                    xmin = min(xmin, obj.Shape.BoundBox.XMin)
                    ymin = min(ymin, obj.Shape.BoundBox.YMin)
                    zmin = min(zmin, obj.Shape.BoundBox.ZMin)
                    xmax = max(xmax, obj.Shape.BoundBox.XMax)
                    ymax = max(ymax, obj.Shape.BoundBox.YMax)
                    zmax = max(zmax, obj.Shape.BoundBox.ZMax)
            except Exception:
                pass
        return xmax - xmin + ymax - ymin + zmax - zmin

    @staticmethod
    def exportStl(freecad_objects, grid, file_path):
        fd, tmp_stl = tempfile.mkstemp(suffix=".ast")
        os.close(fd)
        os.remove(tmp_stl)
        xmin = ymin = zmin = float("inf")
        xmax = ymax = zmax = float("-inf")
        with open(file_path, "w") as f:
            for i in grid.table:
                if i[grid.TYPE] in (
                    "BoxRefine",
                    "CylinderRefine",
                    "SphereRefine",
                    "BoxSet",
                    "CylinderSet",
                    "SphereSet",
                    "BoxTopo",
                    "CylinderTopo",
                    "SphereTopo",
                    "LocationInMesh",
                    "N/A",
                ):
                    continue
                obj = next(
                    (j for j in freecad_objects if i[grid.OBJECT_NAME] == j.Label), None
                )
                if i[grid.TYPE] == "SurfaceRefine":
                    file_name = os.path.join(
                        os.path.dirname(file_path), i[grid.OBJECT_NAME]
                    )
                    Mesh.export([obj], f"{file_name}.ast")  # ascii format
                    os.rename(f"{file_name}.ast", f"{file_name}.stl")  # can overwrite
                else:
                    Mesh.export([obj], tmp_stl)
                    # ascii stlフォーマット
                    # solid 任意の文字列
                    # facet normal x成分値 y成分値 z成分値
                    # outer loop
                    # vertex x成分値 y成分値 z成分値
                    # vertex x成分値 y成分値 z成分値
                    # vertex x成分値 y成分値 z成分値
                    # endloop
                    # endfacet
                    # （facet normal行～endfacet行までを１枚の三角形データとして以降くり返し）
                    # ..............
                    # endsolid 任意の文字列
                    for line in open(tmp_stl, "r"):
                        if "endsolid" in line:
                            f.write(f"endsolid {i[grid.OBJECT_NAME]}\n")
                        elif "solid" in line:
                            f.write(f"solid {i[grid.OBJECT_NAME]}\n")
                        else:
                            f.write(line)
                            if line.lstrip().startswith("vertex"):
                                x, y, z = [float(j) for j in line.split()[1:]]
                                xmin, ymin, zmin = (
                                    min(xmin, x),
                                    min(ymin, y),
                                    min(zmin, z),
                                )
                                xmax, ymax, zmax = (
                                    max(xmax, x),
                                    max(ymax, y),
                                    max(zmax, z),
                                )
                    os.remove(tmp_stl)
        return xmin, ymin, zmin, xmax, ymax, zmax

    @staticmethod
    def makeSurfaceFeatureExtractDict(case_dir_path, surface_file_path, feature_angle):
        dict_path = os.path.join(case_dir_path, "system", "surfaceFeatureExtractDict")
        with open(dict_path, "w") as f:
            f.write(
                "FoamFile\n"
                "{\n"
                "\tversion\t2.0;\n"
                "\tformat\tascii;\n"
                "\tclass\tdictionary;\n"
                '\tlocation\t"system";\n'
                "\tobject\tsurfaceFeatureExtractDict;\n"
                "}\n"
                "\n"
                f"{os.path.basename(surface_file_path)}\n"
                "{\n"
                "\textractionMethod\textractFromSurface;\n"
                "\n"
                "\t// Mark edges whose adjacent surface normals are at an angle less\n"
                "\t// than includedAngle as features\n"
                "\t// - 0  : selects no edges\n"
                "\t// - 180: selects all edges\n"
                f"\tincludedAngle\t{180.0 - float(feature_angle)};\n"
                "\n"
                "\t// Write options\n"
                "\twriteFeatureEdgeMesh\tyes;\n"
                "\n"
                "\t// Write features to obj format for postprocessing\n"
                "\twriteObj\tyes;\n"
                "}\n"
            )
        os.chmod(dict_path, 0o0666)

    @staticmethod
    def makeMeshDict(
        case_dir_path,
        surface_file_path,
        max_cell_size,
        bounding_box,
        freecad_objects,
        grid,
        features_level,
        feature_angle,
        meshDict,
    ):
        meshDict_path = os.path.join(case_dir_path, "system", "snappyHexMeshDict")
        if os.path.isfile(meshDict_path):
            shutil.copy(meshDict_path, f"{meshDict_path}_bak")
        with open(meshDict_path, "w") as f:
            f.write(
                "FoamFile\n"
                "{\n"
                "\tversion\t2.0;\n"
                "\tformat\tascii;\n"
                "\tclass\tdictionary;\n"
                '\tlocation\t"system";\n'
                "\tobject\tsnappyHexMeshDict;\n"
                "}\n"
                "\n"
                "// A manual is available on\n"
                "// https://www.openfoam.com/documentation/guides/latest/doc/guide-meshing-snappyhexmesh.html\n"
            )

            f.write("\n// 実行する工程\n")
            e = dictParse.find_element(
                meshDict,
                [{"type": "dictionary", "key": "castellatedMesh"}, {"type": "word"}],
            )["element"]
            f.write(
                "// - 背景メッシュからSTL形状データに沿って階段状のガタガタなメッシュを切り出す．\n"
                f"castellatedMesh\t{'true' if e is None else e['value']}; // true or false\n"
            )
            e = dictParse.find_element(
                meshDict, [{"type": "dictionary", "key": "snap"}, {"type": "word"}]
            )["element"]
            f.write(
                "// - メッシュを形状にピタッと吸着させる．\n"
                f"snap\t{'true' if e is None else e['value']}; // true or false\n"
            )
            e = dictParse.find_element(
                meshDict, [{"type": "dictionary", "key": "addLayers"}, {"type": "word"}]
            )["element"]
            f.write(
                "// - 壁面に沿った薄い層状のメッシュ（境界層メッシュ）を差し込む．\n"
                f"addLayers\t{'true' if e is None else e['value']}; // true or false\n"
            )

            f.write(
                "\n"
                "CUSTOM_OPTIONS\n"
                "{\n"
                "\t// blockMeshDictファイルを作る時に使う．\n"
                f"\tmaxCellSize\t{max_cell_size};\n"
                f"\tboundingBox\t(({bounding_box[0]} {bounding_box[1]} {bounding_box[2]}) "
                f"({bounding_box[3]} {bounding_box[4]} {bounding_box[5]}));\n"
                "}\n"
            )

            object_names = [i[grid.OBJECT_NAME] for i in grid.table]
            surface_file_path = os.path.basename(surface_file_path)
            surface_file_path_wo_ext = os.path.splitext(surface_file_path)[0]
            f.write(
                "\n"
                "// 面形状の定義．すべての面はsearchableSurfaceクラスに属する．面は以下で使用する：\n"
                "// - 面と交差するメッシュセルの細分化\n"
                "// - 内部/外部/近傍のメッシュセルの細分化\n"
                "// - メッシュ境界を表面にsnapさせる．\n"
                "geometry\n"
                "{\n"
                f"\t{surface_file_path} // in constant/triSurface\n"
                "\t{\n"
                "\t\ttype\ttriSurfaceMesh;\n"
                f"\t\tname\t{surface_file_path_wo_ext};\n"
                "\t}\n"
            )
            for i in grid.table:
                if i[grid.LEVEL] == 0:
                    continue
                if i[grid.TYPE] in ("BoxRefine", "CylinderRefine", "SphereRefine"):
                    obj = next(
                        (j for j in freecad_objects if i[grid.OBJECT_NAME] == j.Label),
                        None,
                    )
                    f.write(f"\n\t{i[grid.OBJECT_NAME]}\n\t{{\n")
                    if i[grid.TYPE] == "BoxRefine":
                        b = obj.Placement.Base
                        m = obj.Placement.Matrix
                        f.write(
                            "\t\ttype\tsearchableRotatedBox;\n"
                            f"\t\tspan\t({obj.Length.Value} {obj.Width.Value} {obj.Height.Value});\n"
                            f"\t\torigin\t({b.x} {b.y} {b.z});\n"
                            f"\t\te1\t({m.A11} {m.A21} {m.A31});\n"
                            f"\t\te3\t({m.A13} {m.A23} {m.A33});\n"
                        )
                    elif i[grid.TYPE] == "CylinderRefine":
                        b = obj.Placement.Base
                        m = obj.Placement.Matrix
                        h = obj.Height.Value
                        f.write(
                            "\t\ttype\tsearchableCylinder;\n"
                            f"\t\tpoint1\t({b.x} {b.y} {b.z});\n"
                            f"\t\tpoint2\t({b.x + m.A13 * h} {b.y + m.A23 * h} {b.z + m.A33 * h});\n"
                            f"\t\tradius\t{obj.Radius.Value};\n"
                        )
                    elif i[grid.TYPE] == "SphereRefine":
                        b = obj.Placement.Base
                        f.write(
                            "\t\ttype\tsearchableSphere;\n"
                            f"\t\tcentre\t({b.x} {b.y} {b.z});\n"
                            f"\t\tradius\t{obj.Radius.Value};\n"
                        )
                    f.write("\t}\n")
                elif i[grid.TYPE] == "SurfaceRefine":
                    f.write(
                        "\n"
                        f"\t{i[grid.OBJECT_NAME]}.stl // in constant/triSurface\n"
                        "\t{\n"
                        "\t\ttype\ttriSurfaceMesh;\n"
                        f"\t\tname\t{i[grid.OBJECT_NAME]};\n"
                        "\t}\n"
                    )
            for block in dictParse.find_all_elements(
                meshDict, [{"type": "block", "key": "geometry"}, {"type": "block"}]
            ):
                block = block["element"]
                if (
                    block["key"] != surface_file_path
                    and block["key"] not in object_names
                ):
                    f.write(f"\n\t{block.file_string(indent_level=1)}\n")
            f.write(
                "\n"
                "//\tboxExample\n"
                "//\t{\n"
                "//\t\ttype\tsearchableBox;\n"
                "//\t\tmin\t(1.5 1 -0.5);\n"
                "//\t\tmax\t(3.5 2 0.5);\n"
                "//\t}\n"
                "\n"
                "//\trotatedBoxExample\n"
                "//\t{\n"
                "//\t\ttype\tsearchableRotatedBox;\n"
                "//\t\tspan\t(5 4 3); // in (e1 e2 e3) directions\n"
                "//\t\torigin\t(0 0 0);\n"
                "//\t\te1\t(1 0.5 0);\n"
                "//\t\te3\t(0 0.5 1);\n"
                "//\t}\n"
                "\n"
                "//\tconeExample\n"
                "//\t{\n"
                "//\t\ttype\tsearchableCone;\n"
                "//\t\tpoint1\t(0 0 0);\n"
                "//\t\tradius1\t1.5;\n"
                "//\t\tinnerRadius1\t0.25;\n"
                "//\t\tpoint2\t(10 0 0);\n"
                "//\t\tradius2\t3.0;\n"
                "//\t\tinnerRadius2\t1.0;\n"
                "//\t}\n"
                "\n"
                "//\tcylinderExample\n"
                "//\t{\n"
                "//\t\ttype\tsearchableCylinder;\n"
                "//\t\tpoint1\t(1.5 1 -0.5);\n"
                "//\t\tpoint2\t(3.5 2 0.5);\n"
                "//\t\tradius\t0.05;\n"
                "//\t}\n"
                "\n"
                "//\tdiskExample\n"
                "//\t{\n"
                "//\t\ttype\tsearchableDisk;\n"
                "//\t\torigin\t(0 0 0);\n"
                "//\t\tnormal\t(0 1 0);\n"
                "//\t\tradius\t0.314;\n"
                "//\t}\n"
                "\n"
                "//\tsphereExample\n"
                "//\t{\n"
                "//\t\ttype\tsearchableSphere;\n"
                "//\t\tcentre\t(0 0 0);\n"
                "//\t\tradius\t3;\n"
                "//\t}\n"
                "}\n"
            )  # geometry

            castellatedMeshControls = dictParse.find_element(
                meshDict, [{"type": "block", "key": "castellatedMeshControls"}]
            )["element"]
            f.write(
                "\n"
                "// castellatedMesh工程の設定\n"
                "castellatedMeshControls\n"
                "{\n"
                "\t// ----- メッシュ細分化パラメータ -----\n"
            )
            e = dictParse.find_element(
                castellatedMeshControls,
                [{"type": "dictionary", "key": "maxLocalCells"}, {"type": "integer"}],
            )["element"]
            f.write(
                "\n"
                "\t// 各CPUコア（プロセス）が保持できる最大セル数\n"
                f"\tmaxLocalCells\t{'100000' if e is None else e['value']};\n"
            )
            e = dictParse.find_element(
                castellatedMeshControls,
                [{"type": "dictionary", "key": "maxGlobalCells"}, {"type": "integer"}],
            )["element"]
            f.write(
                "\n"
                "\t// 全CPUコアの合計セル数の限界値（不要なセルを除去する前の値）\n"
                f"\tmaxGlobalCells\t{'2000000' if e is None else e['value']};\n"
            )
            e = dictParse.find_element(
                castellatedMeshControls,
                [
                    {"type": "dictionary", "key": "minRefinementCells"},
                    {"type": "integer"},
                ],
            )["element"]
            f.write(
                "\n"
                "\t// 細分化するセルの数がminRefinementCells以下になるまでセルを細分化する．\n"
                f"\tminRefinementCells\t{'2' if e is None else e['value']};\n"
            )
            e = dictParse.find_element(
                castellatedMeshControls,
                [
                    {"type": "dictionary", "key": "nCellsBetweenLevels"},
                    {"type": "integer"},
                ],
            )["element"]
            f.write(
                "\n"
                "\t// 異なる細分化レベル間のセルのバッファ層の数\n"
                f"\tnCellsBetweenLevels\t{'3' if e is None else e['value']};\n"
                "\n"
                "\t// ----- 特徴エッジの細分化 -----\n"
                "\n"
                "\t// 特徴エッジと交差するすセルの細分化レベル\n"
                "\tfeatures\n"
                "\t(\n"
                "\t\t{\n"
                f'\t\t\tfile\t"{surface_file_path_wo_ext}.extendedFeatureEdgeMesh";\n'
                f"\t\t\tlevel\t{features_level};\n"
                "\t\t}\n"
                "\t);\n"
                "\n"
                "\t// ----- 面形状の細分化 -----\n"
                "\n"
                "\trefinementSurfaces\n"
                "\t{\n"
                f"\t\t{surface_file_path_wo_ext}\n"
                "\t\t{\n"
            )
            f.write("\t\t\tlevel\t(0 1); // (min max)\n\t\t\tregions\n\t\t\t{\n")
            for i in grid.table:
                if i[grid.TYPE] in (
                    "BoxRefine",
                    "CylinderRefine",
                    "SphereRefine",
                    "SurfaceRefine",
                    "BoxSet",
                    "CylinderSet",
                    "SphereSet",
                    "BoxTopo",
                    "CylinderTopo",
                    "SphereTopo",
                    "LocationInMesh",
                    "N/A",
                ):
                    continue
                f.write(
                    f"\t\t\t\t{i[grid.OBJECT_NAME]}\n"
                    "\t\t\t\t{\n"
                    f"\t\t\t\t\tlevel\t({i[grid.LEVEL]} {i[grid.LEVEL] + 1}); // (min max)\n"
                    "\t\t\t\t\tpatchInfo\t{"
                    f"type\t{i[grid.TYPE]};"
                    "}\n"
                    "\t\t\t\t}\n"
                )
            f.write(
                "\t\t\t}\n"
                "\t\t}\n"
                "\t}\n"
                "\n"
                f"\tresolveFeatureAngle\t{feature_angle};\n"
                "\n"
                "\t// ----- 領域の細分化 -----\n"
                "\n"
                "\trefinementRegions\n"
                "\t{\n"
                "\t\t//                    ********************\n"
                "\t\t//                    ********************   ******************\n"
                "\t\t// +--------------+   **+--------------+**   *+--------------+*\n"
                "\t\t// |**************|   **|              |**   *|**************|*\n"
                "\t\t// |**************|   **|              |**   *|*            *|*\n"
                "\t\t// |*** inside ***|   **|   outside    |**   *|*  distance ->|*<-\n"
                "\t\t// |**************|   **|              |**   *|*          ->*|<-\n"
                "\t\t// |**************|   **|              |**   *|**************|*\n"
                "\t\t// +--------------+   **+--------------+**   *+--------------+*\n"
                "\t\t//                    ********************   ******************\n"
                "\t\t//                    ********************\n"
            )
            for i in grid.table:
                if i[grid.LEVEL] == 0 or i[grid.TYPE] not in (
                    "BoxRefine",
                    "CylinderRefine",
                    "SphereRefine",
                    "SurfaceRefine",
                ):
                    continue
                f.write(f"\n\t\t{i[grid.OBJECT_NAME]}\n\t\t{{\n")
                if i[grid.TYPE] in ("BoxRefine", "CylinderRefine", "SphereRefine"):
                    f.write(
                        "\t\t\tmode\tinside; // distance | inside | outside\n"
                        f"\t\t\tlevels\t((1.0 {i[grid.LEVEL]}));"
                        " // ((distance level)), distanceはmodeがdistanceの時のみ有効\n"
                    )
                else:  # SurfaceRefine
                    f.write(
                        "\t\t\tmode\tdistance;\n"
                        f"\t\t\tlevels\t(({i[grid.RATIO]} {i[grid.LEVEL]}));"
                        " // ((distance1 level1) (distance2 level2) ...), "
                        "distance1 < distance2, level1 > level2\n"
                    )
                f.write("\t\t}\n")
            for block in dictParse.find_all_elements(
                castellatedMeshControls,
                [{"type": "block", "key": "refinementRegions"}, {"type": "block"}],
            ):
                block = block["element"]
                if (
                    block["key"] != surface_file_path
                    and block["key"] not in object_names
                ):
                    f.write(f"\n\t\t{block.file_string(indent_level=2)}\n")
            f.write(
                "\n"
                "//\t\tboxExample // geometryで定義した名前\n"
                "//\t\t{\n"
                "//\t\t\tmode\tinside; // distance | inside | outside\n"
                "//\t\t\tlevels\t((1.0 1)); // ((distance level)), distanceはmodeがdistanceの時のみ有効\n"
                "//\t\t}\n"
                "\t}\n"
                "\n"
                "\t// ----- メッシュ選択 -----\n"
            )
            cellZone = []
            for i in grid.table:
                if i[grid.TYPE] == "LocationInMesh":
                    obj = next(
                        (j for j in freecad_objects if i[grid.OBJECT_NAME] == j.Label),
                        None,
                    )
                    c = obj.Shape.CenterOfMass
                    cellZone.append((c.x, c.y, c.z, i[grid.OBJECT_NAME]))
            if len(cellZone) == 1:
                f.write(
                    "\n"
                    f"\tlocationInMesh\t({cellZone[0][0]} {cellZone[0][1]} {cellZone[0][2]});\n"
                    "\n"
                    "//\tlocationsInMesh\n"
                    "//\t(\n"
                    "//\t\t((0.0 0.0 0.0) zone1)\n"
                    "//\t\t((0.1 0.1 0.1) zone2)\n"
                    "//\t);\n"
                )
            else:
                f.write(
                    "\n//\tlocationInMesh\t(0.0 0.0 0.0)\n\n\tlocationsInMesh\n\t(\n"
                )
                for i in cellZone:
                    f.write(f"\t\t(({i[0]} {i[1]} {i[2]}) {i[3]})\n")
                f.write("\t);\n")
            e = dictParse.find_element(
                castellatedMeshControls,
                [
                    {"type": "dictionary", "key": "allowFreeStandingZoneFaces"},
                    {"type": "word"},
                ],
            )["element"]
            f.write(
                "\n"
                "\t// 通常なら計算領域の中にある面は消されてしまうが，allowFreeStandingZoneFacesがtrueならば，\n"
                "\t// 厚みのない仕切り板（faceZone）としてメッシュに残せる．\n"
                "\t// refinementSurfacesの中でfaceZonesが定義されている場合のみ機能する．\n"
                f"\tallowFreeStandingZoneFaces\t{'true' if e is None else e['value']};\n"
            )
            for element in dictParse.find_all_elements(
                castellatedMeshControls,
                [
                    {
                        "type": "block|dictionary",
                        "except key": (
                            "maxLocalCells"
                            "|"
                            "maxGlobalCells"
                            "|"
                            "minRefinementCells"
                            "|"
                            "nCellsBetweenLevels"
                            "|"
                            "features"
                            "|"
                            "refinementSurfaces"
                            "|"
                            "resolveFeatureAngle"
                            "|"
                            "refinementRegions"
                            "|"
                            "locationInMesh"
                            "|"
                            "locationsInMesh"
                            "|"
                            "allowFreeStandingZoneFaces"
                        ),
                    }
                ],
            ):
                f.write(f"\n\t{element['element'].file_string(indent_level=1)}\n")
            f.write("}\n")  # castellatedMeshControls

            snapControls = dictParse.find_element(
                meshDict, [{"type": "block", "key": "snapControls"}]
            )["element"]
            f.write("\n// snap工程の設定\nsnapControls\n{\n")
            e = dictParse.find_element(
                snapControls,
                [{"type": "dictionary", "key": "nSmoothPatch"}, {"type": "integer"}],
            )["element"]
            f.write(
                "\t// 境界表面を滑らかにする反復回数\n"
                f"\tnSmoothPatch\t{'3' if e is None else e['value']};\n"
            )
            e = dictParse.find_element(
                snapControls,
                [{"type": "dictionary", "key": "nSmoothInternal"}, {"type": "integer"}],
            )["element"]
            f.write(
                "\n"
                "\t// 境界表面を滑らかにした後で歪んでしまった内部メッシュを整える\n"
                "\t// （＝境界のメッシュをなるべく直交させる）反復回数（デフォルト：0）\n"
                f"\tnSmoothInternal\t{'1' if e is None else e['value']};\n"
            )
            e = dictParse.find_element(
                snapControls,
                [{"type": "dictionary", "key": "tolerance"}, {"type": "float|integer"}],
            )["element"]
            f.write(
                "\n"
                "\t// castellatedMeshで作られた階段状の頂点から(局所的なセル長さ)*toleranceの距離まで境界を探し，\n"
                "\t// 見つかった境界に頂点を吸着させる．\n"
                f"\ttolerance\t{'1.0' if e is None else e['value']};\n"
            )
            e = dictParse.find_element(
                snapControls,
                [{"type": "dictionary", "key": "nSolveIter"}, {"type": "integer"}],
            )["element"]
            f.write(
                "\n"
                "\t// メッシュ移動（＝表面への吸着を完遂させる）の反復回数\n"
                f"\tnSolveIter\t{'30' if e is None else e['value']};\n"
            )
            e = dictParse.find_element(
                snapControls,
                [{"type": "dictionary", "key": "nRelaxIter"}, {"type": "integer"}],
            )["element"]
            f.write(
                "\n"
                "\t// メッシュ移動によるメッシュの歪みを緩和する（＝checkMeshエラーを消す）反復回数\n"
                f"\tnRelaxIter\t{'5' if e is None else e['value']};\n"
            )
            e = dictParse.find_element(
                snapControls,
                [
                    {"type": "dictionary", "key": "nFeatureSnapIter"},
                    {"type": "integer"},
                ],
            )["element"]
            f.write(
                "\n"
                "\t// 物体の角や特徴線に対して，メッシュを吸着させる反復回数\n"
                f"\tnFeatureSnapIter\t{'10' if e is None else e['value']};\n"
            )
            for element in dictParse.find_all_elements(
                snapControls,
                [
                    {
                        "type": "block|dictionary",
                        "except key": (
                            "nSmoothPatch"
                            "|"
                            "nSmoothInternal"
                            "|"
                            "tolerance"
                            "|"
                            "nSolveIter"
                            "|"
                            "nRelaxIter"
                            "|"
                            "nFeatureSnapIter"
                        ),
                    }
                ],
            ):
                f.write(f"\n\t{element['element'].file_string(indent_level=1)}\n")
            f.write("}\n")  # snapControls

            addLayersControls = dictParse.find_element(
                meshDict, [{"type": "block", "key": "addLayersControls"}]
            )["element"]
            f.write(
                "\n"
                "// addLayers工程の設定\n"
                "addLayersControls\n"
                "{\n"
                "\t// addLayersControlsの中で指定されるthicknessの設定．\n"
                "\t// relativeSizesがtrueだと，細分化後のセルサイズに対して相対的なものになる．\n"
                "\t// falseだと，メートル単位の長さになる．\n"
                "\trelativeSizes\ttrue;\n"
            )
            f.write("\n\t// 最終パッチにおける境界層メッシュの設定\n\tlayers\n\t{\n")
            for i in grid.table:
                if not i[grid.BOUNDARY_LAYER] or i[grid.TYPE] in (
                    "BoxRefine",
                    "CylinderRefine",
                    "SphereRefine",
                    "SurfaceRefine",
                    "BoxSet",
                    "CylinderSet",
                    "SphereSet",
                    "BoxTopo",
                    "CylinderTopo",
                    "SphereTopo",
                    "LocationInMesh",
                    "N/A",
                ):
                    continue
                f.write(
                    f"\t\t{surface_file_path_wo_ext}_{i[grid.OBJECT_NAME]}\n"
                    "\t\t{\n"
                    f"\t\t\tnSurfaceLayers\t{i[grid.N_LAYERS]};\n"
                    f"\t\t\texpansionRatio\t{i[grid.RATIO]};\n"
                )
                for element in dictParse.find_all_elements(
                    addLayersControls,
                    [
                        {"type": "block", "key": "layers"},
                        {
                            "type": "block",
                            "key": f"{surface_file_path_wo_ext}_{i[grid.OBJECT_NAME]}",
                        },
                        {
                            "type": "block|dictionary",
                            "except key": "nSurfaceLayers|expansionRatio",
                        },
                    ],
                ):
                    f.write(f"\t\t\t{element['element'].file_string(indent_level=3)}\n")
                f.write("\t\t}\n")
            f.write("\t}\n")  # layers
            e = dictParse.find_element(
                addLayersControls,
                [
                    {"type": "dictionary", "key": "expansionRatio"},
                    {"type": "float|integer"},
                ],
            )["element"]
            f.write(
                f"\texpansionRatio\t{'1' if e is None else e['value']}; // mandatory\n"
            )
            e = dictParse.find_element(
                addLayersControls,
                [
                    {"type": "dictionary", "key": "finalLayerThickness"},
                    {"type": "float|integer"},
                ],
            )["element"]
            f.write(
                "\n"
                "\t// 壁から最も遠い境界層メッシュの厚さ\n"
                f"\tfinalLayerThickness\t{'1' if e is None else e['value']};\n"
            )
            e = dictParse.find_element(
                addLayersControls,
                [
                    {"type": "dictionary", "key": "minThickness"},
                    {"type": "float|integer"},
                ],
            )["element"]
            f.write(
                "\n"
                "\t// minThickness以下の厚さになるのであれば，その場所には境界層メッシュを追加しない．\n"
                f"\tminThickness\t{'0.1' if e is None else e['value']};\n"
            )
            e = dictParse.find_element(
                addLayersControls,
                [{"type": "dictionary", "key": "nGrow"}, {"type": "integer"}],
            )["element"]
            f.write(
                "\n"
                "\t// 狭くて境界層メッシュを追加できない点を中心にして，\n"
                "\t// nGrow個分の境界層メッシュの範囲には境界層メッシュを追加しない．\n"
                f"\tnGrow\t{'0' if e is None else e['value']};\n"
            )
            f.write(
                "\n"
                "\t// ----- 詳細設定 -----\n"
                "\n"
                "\t// 隣り合う面の角度がfeatureAngleより大きいと，その場所には境界層メッシュを追加しない．\n"
                f"\tfeatureAngle\t{feature_angle};\n"
            )
            e = dictParse.find_element(
                addLayersControls,
                [{"type": "dictionary", "key": "nRelaxIter"}, {"type": "integer"}],
            )["element"]
            f.write(
                "\n"
                "\t// 境界層メッシュが追加されたことによるメッシュの歪みを緩和する（＝checkMeshエラーを消す）反復回数\n"
                f"\tnRelaxIter\t{'3' if e is None else e['value']};\n"
            )
            e = dictParse.find_element(
                addLayersControls,
                [
                    {"type": "dictionary", "key": "nSmoothSurfaceNormals"},
                    {"type": "integer"},
                ],
            )["element"]
            f.write(
                "\n"
                "\t// 壁面から境界層メッシュを追加する方向（法線方向）を整える反復回数\n"
                f"\tnSmoothSurfaceNormals\t{'1' if e is None else e['value']};\n"
            )
            e = dictParse.find_element(
                addLayersControls,
                [{"type": "dictionary", "key": "nSmoothNormals"}, {"type": "integer"}],
            )["element"]
            f.write(
                "\n"
                "\t// 境界層メッシュの追加により歪んだ内側メッシュを整える反復回数\n"
                f"\tnSmoothNormals\t{'3' if e is None else e['value']};\n"
            )
            e = dictParse.find_element(
                addLayersControls,
                [
                    {"type": "dictionary", "key": "nSmoothThickness"},
                    {"type": "integer"},
                ],
            )["element"]
            f.write(
                "\n"
                "\t// メッシュを整える領域の厚さ\n"
                f"\tnSmoothThickness\t{'10' if e is None else e['value']};\n"
            )
            e = dictParse.find_element(
                addLayersControls,
                [
                    {"type": "dictionary", "key": "maxFaceThicknessRatio"},
                    {"type": "float|integer"},
                ],
            )["element"]
            f.write(
                "\n"
                "\t// メッシュセルのアスペクト比がmaxFaceThicknessRatioより小さいと，境界層メッシュを追加しない．\n"
                f"\tmaxFaceThicknessRatio\t{'0.5' if e is None else e['value']};\n"
            )
            e = dictParse.find_element(
                addLayersControls,
                [
                    {"type": "dictionary", "key": "maxThicknessToMedialRatio"},
                    {"type": "float|integer"},
                ],
            )["element"]
            f.write(
                "\n"
                "\t// 流路幅に対する境界層メッシュの厚さがmaxThicknessToMedialRatioより大きい所では，\n"
                "\t// 境界層メッシュを薄くしたり，追加しない．\n"
                f"\tmaxThicknessToMedialRatio\t{'1' if e is None else e['value']};\n"
            )
            e = dictParse.find_element(
                addLayersControls,
                [
                    {"type": "dictionary", "key": "minMedialAxisAngle"},
                    {"type": "float|integer"},
                ],
            )["element"]
            f.write(
                "\n"
                "\t// 向かい合う壁からの法線が交差する角度がminMedialAxisAngleよりも大きい場合，\n"
                "\t// 対面する壁がある狭い場所とみなす．\n"
                f"\tminMedialAxisAngle\t{'90' if e is None else e['value']};\n"
            )
            e = dictParse.find_element(
                addLayersControls,
                [
                    {"type": "dictionary", "key": "nBufferCellsNoExtrude"},
                    {"type": "float|integer"},
                ],
            )["element"]
            f.write(
                "\n"
                "\t// 境界層メッシュが追加される領域とされない領域の境界に設ける，緩衝セルの数\n"
                f"\tnBufferCellsNoExtrude\t{'0' if e is None else e['value']};\n"
            )
            e = dictParse.find_element(
                addLayersControls,
                [{"type": "dictionary", "key": "nLayerIter"}, {"type": "integer"}],
            )["element"]
            f.write(
                "\n"
                "\t// 境界層メッシュを追加する工程の反復回数\n"
                f"\tnLayerIter\t{'50' if e is None else e['value']};\n"
            )
            e = dictParse.find_element(
                addLayersControls,
                [{"type": "dictionary", "key": "nRelaxedIter"}, {"type": "integer"}],
            )["element"]
            f.write(
                "\n"
                "\t// 境界層メッシュを追加する工程の最終段階で，\n"
                "\t// メッシュ品質の基準を少し緩めて（Relaxed）追加で修正を行う反復回数\n"
                f"\tnRelaxedIter\t{'50' if e is None else e['value']};\n"
            )
            for element in dictParse.find_all_elements(
                addLayersControls,
                [
                    {
                        "type": "block|dictionary",
                        "except key": (
                            "relativeSizes"
                            "|"
                            "layers"
                            "|"
                            "expansionRatio"
                            "|"
                            "finalLayerThickness"
                            "|"
                            "minThickness"
                            "|"
                            "nGrow"
                            "|"
                            "featureAngle"
                            "|"
                            "nRelaxIter"
                            "|"
                            "nSmoothSurfaceNormals"
                            "|"
                            "nSmoothNormals"
                            "|"
                            "nSmoothThickness"
                            "|"
                            "maxFaceThicknessRatio"
                            "|"
                            "maxThicknessToMedialRatio"
                            "|"
                            "minMedialAxisAngle"
                            "|"
                            "nBufferCellsNoExtrude"
                            "|"
                            "nLayerIter"
                            "|"
                            "nRelaxedIter"
                        ),
                    }
                ],
            ):
                f.write(f"\n\t{element['element'].file_string(indent_level=1)}\n")
            f.write("}\n")  # addLayersControls

            meshQualityControls = dictParse.find_element(
                meshDict, [{"type": "block", "key": "meshQualityControls"}]
            )["element"]
            f.write(
                "\n"
                "// メッシュ品質の設定\n"
                "meshQualityControls\n"
                "{\n"
                '\t#includeEtc "caseDicts/meshQualityDict"\n'
                "\n"
                "\t// メッシュ品質の基準を緩めたとき（Relaxed）に，どこまで妥協して良いか\n"
                "\t// addLayersControls.nRelaxedIterなどで使う．\n"
                "\trelaxed\n"
                "\t{\n"
            )
            e = dictParse.find_element(
                meshQualityControls,
                [
                    {"type": "block", "key": "relaxed"},
                    {"type": "dictionary", "key": "maxNonOrtho"},
                    {"type": "float|integer"},
                ],
            )["element"]
            f.write(
                "\t\t// 非直交の許容角度．180だと全てを許容する.\n"
                f"\t\tmaxNonOrtho\t{'75' if e is None else e['value']};\n"
            )
            for element in dictParse.find_all_elements(
                meshQualityControls,
                [
                    {"type": "block", "key": "relaxed"},
                    {"type": "block|dictionary", "except key": "maxNonOrtho"},
                ],
            ):
                f.write(f"\n\t\t{element['element'].file_string(indent_level=2)}\n")
            f.write("\t}\n\n\t// ----- 詳細設定 -----\n")
            e = dictParse.find_element(
                meshQualityControls,
                [{"type": "dictionary", "key": "nSmoothScale"}, {"type": "integer"}],
            )["element"]
            f.write(
                "\n"
                "\t// 境界層メッシュの厚みの制限倍率（Scale field）を平滑化する反復回数\n"
                "\t// errorReductionと一緒に使う．\n"
                f"\tnSmoothScale\t{'4' if e is None else e['value']};\n"
            )
            e = dictParse.find_element(
                meshQualityControls,
                [
                    {"type": "dictionary", "key": "errorReduction"},
                    {"type": "float|integer"},
                ],
            )["element"]
            f.write(
                "\n"
                "\t// 境界層メッシュの品質のエラーが発生した場所で，厚さをerrorReduction倍薄くする．\n"
                "\t// nSmoothScaleと一緒に使う．\n"
                f"\terrorReduction\t{'0.75' if e is None else e['value']};\n"
            )
            for element in dictParse.find_all_elements(
                meshQualityControls,
                [
                    {
                        "type": "block|dictionary",
                        "except key": "relaxed|nSmoothScale|errorReduction",
                    }
                ],
            ):
                f.write(f"\n\t{element['element'].file_string(indent_level=1)}\n")
            f.write("}\n")  # meshQualityControls

            e = dictParse.find_element(
                meshDict,
                [{"type": "block", "key": "mergeTolerance"}, {"type": "float|integer"}],
            )["element"]
            f.write(
                "\n"
                "// ----- 詳細設定 -----\n"
                "\n"
                "// 離れている2つの点を，同じ場所にあるとみなして1つに統合（マージ）する距離のしきい値\n"
                f"\tmergeTolerance\t{'1.0e-06' if e is None else e['value']};\n"
            )

            for element in dictParse.find_all_elements(
                meshDict,
                [
                    {
                        "type": "block|dictionary",
                        "except key": (
                            "FoamFile"
                            "|"
                            "castellatedMesh"
                            "|"
                            "snap"
                            "|"
                            "addLayers"
                            "|"
                            "CUSTOM_OPTIONS"
                            "|"
                            "geometry"
                            "|"
                            "castellatedMeshControls"
                            "|"
                            "snapControls"
                            "|"
                            "addLayersControls"
                            "|"
                            "meshQualityControls"
                            "|"
                            "mergeTolerance"
                        ),
                    }
                ],
            ):
                f.write(f"\n{element['element'].file_string()}\n")

        os.chmod(meshDict_path, 0o0666)

    @staticmethod
    def makeSetFieldsDict(case_dir_path, freecad_objects, grid, setFieldsDict):
        if not any(
            (i[grid.TYPE] in ("BoxSet", "CylinderSet", "SphereSet") for i in grid.table)
        ):
            return
        dict_path = os.path.join(case_dir_path, "system", "setFieldsDict")
        if os.path.isfile(dict_path):
            shutil.copy(dict_path, f"{dict_path}_bak")

        with open(dict_path, "w") as f:
            f.write(
                "FoamFile\n"
                "{\n"
                "\tversion\t2.0;\n"
                "\tformat\tascii;\n"
                "\tclass\tdictionary;\n"
                '\tlocation\t"system";\n'
                "\tobject\tsetFieldsDict;\n"
                "}\n"
                "\n"
            )

            defaultFieldValues = dictParse.find_element(
                setFieldsDict, [{"type": "dictionary", "key": "defaultFieldValues"}]
            )["element"]
            if defaultFieldValues is not None:
                f.write(f"{defaultFieldValues.file_string()}\n")
            else:
                f.write(
                    "defaultFieldValues // regionsで指定しない領域における値\n"
                    "(\n"
                    "\tvolScalarFieldValue\talpha.water 0 // ←自分の目的に合わせて書き換える\n"
                    "\tvolVectorFieldValue\tU ( 0 0 0 ) // ←自分の目的に合わせて書き換える\n"
                    ");\n"
                )

            regions = dictParse.find_element(
                setFieldsDict,
                [{"type": "dictionary", "key": "regions"}, {"type": "list"}],
            )["element"]
            f.write("\nregions\n(\n")
            for i in grid.table:
                if i[grid.TYPE] not in ("BoxSet", "CylinderSet", "SphereSet"):
                    continue
                obj = next(
                    (j for j in freecad_objects if i[grid.OBJECT_NAME] == j.Label), None
                )
                if i[grid.TYPE] == "BoxSet":
                    b = obj.Shape.BoundBox
                    f.write(
                        f"\tboxToCell // Object {i[grid.OBJECT_NAME]} in FreeCAD\n"
                        "\t{\n"
                        f"\t\tbox\t({0.001 * b.XMin} {0.001 * b.YMin} {0.001 * b.ZMin}) "
                        f"({0.001 * b.XMax} {0.001 * b.YMax} {0.001 * b.ZMax});\n"
                    )
                elif i[grid.TYPE] == "CylinderSet":
                    b = obj.Placement.Base
                    m = obj.Placement.Matrix
                    h = obj.Height.Value
                    f.write(
                        f"\tcylinderToCell // Object {i[grid.OBJECT_NAME]} in FreeCAD\n"
                        "\t{\n"
                        f"\t\tp1\t({0.001 * b.x} {0.001 * b.y} {0.001 * b.z});\n"
                        f"\t\tp2\t({0.001 * (b.x + m.A13 * h)} {0.001 * (b.y + m.A23 * h)} {0.001 * (b.z + m.A33 * h)});\n"
                        f"\t\tradius\t{0.001 * obj.Radius.Value};\n"
                    )
                else:  # SphereSet
                    b = obj.Placement.Base
                    f.write(
                        f"\tsphereToCell // Object {i[grid.OBJECT_NAME]} in FreeCAD\n"
                        "\t{\n"
                        f"\t\tcentre\t({0.001 * b.x} {0.001 * b.y} {0.001 * b.z});\n"
                        f"\t\tradius\t{0.001 * obj.Radius.Value};\n"
                    )
                for comment in dictParse.find_all_elements(
                    regions, [{"type": "block"}, {"type": "line_comment|block_comment"}]
                ):
                    if i[grid.OBJECT_NAME] not in comment["element"]["value"]:
                        continue
                    fieldValues = dictParse.find_element(
                        comment["parent"],
                        [{"type": "dictionary", "key": "fieldValues"}],
                    )["element"]
                    if fieldValues is None:
                        f.write(
                            "\t\tfieldValues\n"
                            "\t\t(\n"
                            "\t\t\tvolScalarFieldValue alpha.water 1 // ←自分の目的に合わせて書き換える\n"
                            "\t\t);\n"
                        )
                    else:
                        f.write(f"\t\t{fieldValues.file_string(indent_level=2)}\n")
                f.write("\t}\n")  # boxToCell, cylinderToCell, sphereToCell
            for block in dictParse.find_all_elements(regions, [{"type": "block"}]):
                block = block["element"]
                comment = dictParse.find_element(
                    block, [{"type": "line_comment|block_comment"}]
                )["element"]["value"]
                if "freecad" not in comment.lower():
                    f.write(f"\n\t{block.file_string(indent_level=1)}\n")
                f.write(");\n")  # regions

            for element in dictParse.find_all_elements(
                setFieldsDict,
                [
                    {
                        "type": "block|dictionary",
                        "except key": "FoamFile|defaultFieldValues|regions",
                    }
                ],
            ):
                f.write(f"\n{element['element'].file_string()}\n")

        os.chmod(dict_path, 0o0666)

    @staticmethod
    def makeTopoSetDict(case_dir_path, freecad_objects, grid, topoSetDict):
        if not any((i[grid.TYPE] == "BoxTopo" for i in grid.table)):
            return
        dict_path = os.path.join(case_dir_path, "system", "topoSetDict")
        if os.path.isfile(dict_path):
            shutil.copy(dict_path, f"{dict_path}_bak")

        with open(dict_path, "w") as f:
            f.write(
                "FoamFile\n"
                "{\n"
                "\tversion\t2.0;\n"
                "\tformat\tascii;\n"
                "\tclass\tdictionary;\n"
                '\tlocation\t"system";\n'
                "\tobject\ttopoSetDict;\n"
                "}\n"
            )  # FoamFile

            actions = dictParse.DictParser.find_all_element_static(
                [
                    {"type": "dictionary", "key": "actions"},
                    {"type": "list"},
                    {"type": "block"},
                ],
                parent=topoSetDict,
            )
            f.write("\nactions\n(\n")
            for i in grid.table:
                if i[grid.TYPE] not in ("BoxTopo", "CylinderTopo", "SphereTopo"):
                    continue
                block = next(
                    (
                        i["element"]
                        for i in actions
                        if dictParse.find_element(
                            i["element"],
                            [
                                {"type": "dictionary", "key": "name"},
                                {
                                    "type": "word",
                                    "value": f"{i[grid.OBJECT_NAME]}CellSet",
                                },
                            ],
                        )["element"]
                        is not None
                    ),
                    None,
                )
                if block is None:
                    action = "new"
                else:
                    action = dictParse.find_element(
                        block,
                        [{"type": "dictionary", "key": "action"}, {"type": "word"}],
                    )["element"]
                    if action is None:
                        action = "new"
                f.write(
                    "\t{"
                    f" // Object {i[grid.OBJECT_NAME]} in FreeCAD\n"
                    f"\t\tname\t{i[grid.OBJECT_NAME]}CellSet;\n"
                    "\t\ttype\tcellSet;\n"
                    f"\t\taction\t{action};\t// new | add | subtract\n"
                )
                obj = next(
                    (j for j in freecad_objects if i[grid.OBJECT_NAME] == j.Label), None
                )
                if i[grid.TYPE] == "BoxTopo":
                    b = obj.Placement.Base
                    m = obj.Placement.Matrix
                    l = obj.Length.Value
                    w = obj.Width.Value
                    h = obj.Height.Value
                    f.write(
                        "\t\tsource\trotatedBoxToCell;\n"
                        f"\t\torigin\t({0.001 * b.x} {0.001 * b.y} {0.001 * b.z});\n"
                        f"\t\ti\t({0.001 * l * m.A11} {0.001 * l * m.A21} {0.001 * l * m.A31});\n"
                        f"\t\tj\t({0.001 * w * m.A12} {0.001 * w * m.A22} {0.001 * w * m.A32});\n"
                        f"\t\tk\t({0.001 * h * m.A13} {0.001 * h * m.A23} {0.001 * h * m.A33});\n"
                    )
                elif i[grid.TYPE] == "CylinderTopo":
                    b = obj.Placement.Base
                    m = obj.Placement.Matrix
                    h = obj.Height.Value
                    f.write(
                        "\t\tsource\tcylinderToCell;\n"
                        f"\t\tp1\t({0.001 * b.x} {0.001 * b.y} {0.001 * b.z});\n"
                        f"\t\tp2\t({0.001 * (b.x + m.A13 * h)} {0.001 * (b.y + m.A23 * h)} {0.001 * (b.z + m.A33 * h)});\n"
                        f"\t\tradius\t{0.001 * obj.Radius.Value};\n"
                    )
                else:  # SphereTopo
                    b = obj.Placement.Base
                    f.write(
                        "\t\tsource\tsphereToCell;\n"
                        f"\t\torigin\t({0.001 * b.x} {0.001 * b.y} {0.001 * b.z});\n"
                        f"\t\tradius\t{0.001 * obj.Radius.Value};\n"
                    )
                f.write("\t}\n")
            for i in grid.table:
                if i[grid.TYPE] in ("BoxTopo", "CylinderTopo", "SphereTopo"):
                    f.write(
                        "\t{"
                        f" // Object {i[grid.OBJECT_NAME]} in FreeCAD\n"
                        f"\t\tname\t{i[grid.OBJECT_NAME]};\n"
                        "\t\ttype\tcellZoneSet;\n"
                        "\t\taction\tnew;\n"
                        "\t\tsource\tsetToCellZone;\n"
                        f"\t\tset\t{i[grid.OBJECT_NAME]}CellSet;\n"
                        "\t}\n"
                    )
            written_action_names = "|".join(
                [
                    f"{i[grid.OBJECT_NAME]}|{i[grid.OBJECT_NAME]}CellSet"
                    for i in grid.table
                ]
            )
            for block in actions:
                block = ["element"]
                if (
                    dictParse.find_element(
                        block,
                        [
                            {"type": "dictionary", "key": "name"},
                            {"type": "word", "except value": written_action_names},
                        ],
                    )["element"]
                    is not None
                ):
                    f.write(f"\n\t{block.file_string(indent_level=1)}\n")
            f.write(");\n")  # actions

            for element in dictParse.find_all_elements(
                topoSetDict,
                [{"type": "block|dictionary", "except key": "FoamFile|actions"}],
            ):
                f.write(f"\n{element['element'].file_string()}\n")

        os.chmod(dict_path, 0o0666)


if __name__ == "__main__":
    MyController()
