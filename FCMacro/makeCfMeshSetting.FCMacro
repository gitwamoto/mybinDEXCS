#!/usr/bin/env python
# -*- coding: utf-8 -*-
# makeCfMeshSetting.FCMacro
# by Yukiharu Iwamoto
# 2026/10/23 1:25:11 PM

VERSION = "2026/10/23 1:25:11 PM"

from PySide import QtCore, QtGui
from functools import partial
import os
import shutil
import tempfile
import Mesh
import re
import sys
import subprocess
import glob

binDEXCS_path = os.path.expanduser(
    "~/Desktop/binDEXCS（解析フォルダを端末で開いてから）"
)  # dakuten.py -j -f <path> で濁点を結合しておく
if binDEXCS_path not in sys.path:
    sys.path.append(binDEXCS_path)
from utilities import dictParse

cases_path = "cases_for_cfmesh"
pat_region_boundary = re.compile(  # マルチリージョン解析の時の領域境界名のパターン
    r"(?P<region_from>(?:(?!\.to\.).)+)\.to\.(?P<region_to>(?:(?!\.[0-9]+$).)+)"
    r"(?:\.(?P<number>[0-9]+))?$"
)


class FreeCadFileGrid(QtGui.QTableWidget):
    OBJECT_NAME = 0
    TYPE = 1
    CELL_SIZE = 2
    BOUNDARY_LAYER = 3
    N_LAYERS = 4
    RATIO = 5

    COL_LABELS = [
        "OjbectName",
        "Type",
        "CellSize",
        "Boundary\nLayer",
        "nLayers",
        "Ratio/Thickness\nfor SurfaceRefine",
    ]

    def __init__(self, parent, freecad_objects):
        super(FreeCadFileGrid, self).__init__(parent)
        pat = re.compile(
            r"[\x20-\x7E]+$"
        )  # 半角の英数字と標準的な半角記号（ASCII範囲内）のみ許可する正規表現
        self.table = []
        for obj in freecad_objects:
            try:
                if (
                    obj.ViewObject.Visibility
                    and hasattr(obj, "Shape")
                    and "PartDesign::"
                    not in obj.TypeId  # Bodyや押し出しなどのフィーチャーを排除
                    and not hasattr(obj, "Role")  # 軸や原点を排除
                ):
                    if pat.match(obj.Label) is None:
                        QtGui.QMessageBox.critical(
                            None,
                            "動作保証外",
                            f"ラベル{obj.Label}が全角文字を含んでいます．\n"
                            "動作が保証できません．半角文字で名前をつけ直して下さい．",
                            QtGui.QMessageBox.Close,
                        )
                        raise ValueError("zenkaku label")
                    self.table.append([obj.Label, None, "", False, 2, 1.2])
            except ValueError:
                raise
            except Exception:
                print(sys.exc_info())
        self.setRowCount(len(self.table))
        self.setColumnCount(len(self.table[0]))
        self.setHorizontalHeaderLabels(FreeCadFileGrid.COL_LABELS)
        self.horizontalHeader().setResizeMode(QtGui.QHeaderView.ResizeToContents)
        self.horizontalHeader().setResizeMode(
            FreeCadFileGrid.OBJECT_NAME, QtGui.QHeaderView.Stretch
        )
        for i in range(self.rowCount()):
            item = QtGui.QTableWidgetItem(
                str(self.table[i][FreeCadFileGrid.OBJECT_NAME])
            )
            item.setFlags(item.flags() & ~QtCore.Qt.ItemIsEditable)
            item.setTextAlignment(QtCore.Qt.AlignCenter)
            self.setItem(i, FreeCadFileGrid.OBJECT_NAME, item)
            for j in (
                FreeCadFileGrid.CELL_SIZE,
                FreeCadFileGrid.N_LAYERS,
                FreeCadFileGrid.RATIO,
            ):
                item = QtGui.QTableWidgetItem(str(self.table[i][j]))
                item.setTextAlignment(QtCore.Qt.AlignRight)
                self.setItem(i, j, item)
            combo = QtGui.QComboBox()
            combo.addItems(
                [
                    "patch",
                    "wall",
                    "empty",
                    "symmetryPlane",
                    "symmetry",
                    "overset",
                    "mappedWall",
                    "BoxRefine",
                    "CylinderRefine",
                    "SphereRefine",
                    "SurfaceRefine",
                    "BoxSet",
                    "CylinderSet",
                    "SphereSet",
                    "BoxTopo",
                    "CylinderTopo",
                    "SphereTopo",
                    "N/A",
                ]
            )
            self.setCellWidget(i, FreeCadFileGrid.TYPE, combo)
            self.table[i][FreeCadFileGrid.TYPE] = combo.itemText(combo.currentIndex())
            combo.currentIndexChanged.connect(
                partial(self.actionOnCurrentIndexChanged, i)
            )
            check = QtGui.QCheckBox()
            self.setCellWidget(i, FreeCadFileGrid.BOUNDARY_LAYER, check)
            self.table[i][FreeCadFileGrid.BOUNDARY_LAYER] = check.isChecked()
            check.stateChanged.connect(partial(self.actionOnStateChanged, i))
        self.cellChanged.connect(self.actionOnCellChanged)

    def actionOnCurrentIndexChanged(self, row, index):
        self.updateTable(
            row,
            FreeCadFileGrid.TYPE,
            self.cellWidget(row, FreeCadFileGrid.TYPE).itemText(index),
        )

    def actionOnStateChanged(self, row, state):
        try:
            self.updateTable(
                row, FreeCadFileGrid.BOUNDARY_LAYER, state == QtCore.Qt.Checked.value
            )
        except Exception:
            self.updateTable(
                row, FreeCadFileGrid.BOUNDARY_LAYER, state == QtCore.Qt.Checked
            )

    def actionOnCellChanged(self, row, col):
        try:
            self.updateTable(row, col, self.item(row, col).text())
        except Exception:
            self.item(row, col).setText(str(self.table[row][col]))

    def updateTable(self, row, col, value):
        try:
            if col == FreeCadFileGrid.CELL_SIZE:
                if value == "":
                    self.table[row][col] = value
                else:
                    self.table[row][col] = float(value)
            elif col == FreeCadFileGrid.N_LAYERS:
                self.table[row][col] = int(value)
            elif col == FreeCadFileGrid.RATIO:
                self.table[row][col] = float(value)
            else:
                self.table[row][col] = value
        except Exception:
            raise

    def setCellValue(self, row, col, value):
        try:
            self.updateTable(row, col, value)
            if col == FreeCadFileGrid.TYPE:
                self.cellWidget(row, FreeCadFileGrid.TYPE).setCurrentIndex(
                    self.cellWidget(row, FreeCadFileGrid.TYPE).findText(value)
                )
            elif col == FreeCadFileGrid.BOUNDARY_LAYER:
                self.cellWidget(row, FreeCadFileGrid.BOUNDARY_LAYER).setCheckState(
                    QtCore.Qt.Checked if value else QtCore.Qt.Unchecked
                )
            else:
                self.item(row, col).setText(value)
        except Exception:
            pass


class MeshFrame(QtGui.QDialog):
    def __init__(
        self, controller, freecad_objects, case_dir_path, max_cell_size, feature_angle
    ):
        if (
            re.match(r"[\x20-\x7E]+$", os.path.basename(case_dir_path)) is None
        ):  # 半角の英数字と標準的な半角記号（ASCII範囲内）のみ許可する正規表現
            QtGui.QMessageBox.critical(
                None,
                "動作保証外",
                f"解析フォルダ名{os.path.basename(case_dir_path)}が全角文字を含んでいます．\n"
                "動作が保証できません．半角文字で名前をつけ直して下さい．",
                QtGui.QMessageBox.Close,
            )
            raise ValueError("zenkaku path")

        super(MeshFrame, self).__init__(parent=None)
        self.setWindowTitle(f"cfMesh settings from FreeCAD Model (.fcstd), {VERSION}")

        self.controller = controller

        box_V = QtGui.QVBoxLayout()
        self.setLayout(box_V)

        box_H = QtGui.QHBoxLayout()
        box_V.addLayout(box_H)
        self.caseButton = QtGui.QPushButton("Case directory:")
        self.caseButton.setSizePolicy(QtGui.QSizePolicy.Fixed, QtGui.QSizePolicy.Fixed)
        self.caseButton.clicked.connect(self.controller.actionOnCaseButton)
        box_H.addWidget(self.caseButton)
        self.caseDirST = QtGui.QLabel(case_dir_path)
        box_H.addWidget(self.caseDirST)
        self.openButton = QtGui.QPushButton("xdg-open")
        self.openButton.setSizePolicy(QtGui.QSizePolicy.Fixed, QtGui.QSizePolicy.Fixed)
        self.openButton.clicked.connect(self.controller.actionOnOpenButton)
        box_H.addWidget(self.openButton)

        box_H = QtGui.QHBoxLayout()
        box_V.addLayout(box_H)
        box_H.addWidget(QtGui.QLabel("maxCellSize:"))
        self.maxCellSizeCRL = QtGui.QLineEdit(f"{max_cell_size:.2f}")
        self.maxCellSizeCRL.setAlignment(QtCore.Qt.AlignRight)
        self.maxCellSizeCRL.setValidator(QtGui.QDoubleValidator())
        box_H.addWidget(self.maxCellSizeCRL)
        box_H.addItem(QtGui.QSpacerItem(12, 0))
        box_H.addWidget(QtGui.QLabel("minCellSize:"))
        self.minCellSizeCRL = QtGui.QLineEdit()
        self.minCellSizeCRL.setAlignment(QtCore.Qt.AlignRight)
        self.minCellSizeCRL.setValidator(QtGui.QDoubleValidator())
        box_H.addWidget(self.minCellSizeCRL)
        box_H.addItem(QtGui.QSpacerItem(12, 0))
        box_H.addWidget(QtGui.QLabel("featureAngle:"))
        self.featureAngleCRL = QtGui.QLineEdit(f"{feature_angle}")
        self.featureAngleCRL.setAlignment(QtCore.Qt.AlignRight)
        self.featureAngleCRL.setValidator(QtGui.QDoubleValidator())
        box_H.addWidget(self.featureAngleCRL)

        self.grid = FreeCadFileGrid(self, freecad_objects)
        box_V.addWidget(self.grid)
        box_V.addWidget(
            QtGui.QLabel(
                "※ 上の表は全ての可視オブジェクトを含んでいます.\n"
                "     可視性（Visibility）を切り替えるには，オブジェクトを選んだ後でスペースキーを押します．\n"
                "※ マルチリージョン解析の場合，以下のルールでOjbectNameを決めて下さい：\n"
                "    mappedWall以外で，1つだけの領域に含めたい場合 → 領域名.物体名\n"
                "    mappedWallの場合 → 自分の領域名.to.相手の領域名    または    自分の領域名.to.相手の領域名.数字\n"
                "        ※ 相手の領域名.to.自分の領域名 の境界は自動で作成されます．"
            )
        )

        box_H = QtGui.QHBoxLayout()
        box_V.addLayout(box_H)
        self.exportButton = QtGui.QPushButton("Export")
        self.exportButton.setSizePolicy(
            QtGui.QSizePolicy.Fixed, QtGui.QSizePolicy.Fixed
        )
        self.exportButton.clicked.connect(self.controller.actionOnExportButton)
        box_H.addWidget(self.exportButton)
        box_H.addWidget(QtGui.QLabel("->"))
        self.cartesianMeshButton = QtGui.QPushButton("cartesianMesh")
        self.cartesianMeshButton.setSizePolicy(
            QtGui.QSizePolicy.Fixed, QtGui.QSizePolicy.Fixed
        )
        self.cartesianMeshButton.clicked.connect(
            self.controller.actionOnCartesianMeshButton
        )
        box_H.addWidget(self.cartesianMeshButton)
        box_H.addWidget(QtGui.QLabel("( ->"))
        self.improveMeshQualityButton = QtGui.QPushButton("improveMeshQuality")
        self.improveMeshQualityButton.setSizePolicy(
            QtGui.QSizePolicy.Fixed, QtGui.QSizePolicy.Fixed
        )
        self.improveMeshQualityButton.clicked.connect(
            self.controller.actionOnImproveMeshQualityButton
        )
        box_H.addWidget(self.improveMeshQualityButton)
        box_H.addWidget(QtGui.QLabel(","))
        self.flattenPatchButton = QtGui.QPushButton("Flatten patch")
        self.flattenPatchButton.setSizePolicy(
            QtGui.QSizePolicy.Fixed, QtGui.QSizePolicy.Fixed
        )
        self.flattenPatchButton.clicked.connect(
            self.controller.actionOnFlattenPatchButton
        )
        box_H.addWidget(self.flattenPatchButton)
        box_H.addWidget(QtGui.QLabel(")"))
        box_H.addItem(
            QtGui.QSpacerItem(
                40, 20, QtGui.QSizePolicy.Expanding, QtGui.QSizePolicy.Minimum
            )
        )

        box_H = QtGui.QHBoxLayout()
        box_V.addLayout(box_H)
        self.loadButton = QtGui.QPushButton("Load")
        self.loadButton.setSizePolicy(QtGui.QSizePolicy.Fixed, QtGui.QSizePolicy.Fixed)
        self.loadButton.clicked.connect(self.controller.actionOnLoadButton)
        self.loadButton.setDefault(True)
        box_H.addWidget(self.loadButton)
        self.editButton = QtGui.QPushButton("Edit")
        self.editButton.setSizePolicy(QtGui.QSizePolicy.Fixed, QtGui.QSizePolicy.Fixed)
        self.editButton.clicked.connect(self.controller.actionOnEditButton)
        box_H.addWidget(self.editButton)
        box_H.addItem(
            QtGui.QSpacerItem(
                40, 20, QtGui.QSizePolicy.Expanding, QtGui.QSizePolicy.Minimum
            )
        )
        self.exitButton = QtGui.QPushButton("Exit")
        self.exitButton.setSizePolicy(QtGui.QSizePolicy.Fixed, QtGui.QSizePolicy.Fixed)
        self.exitButton.clicked.connect(self.actionOnExitButton)
        box_H.addWidget(self.exitButton)

    def setAllType(self, type_value):
        for i in range(self.grid.rowCount()):
            self.grid.setCellValue(i, self.grid.TYPE, type_value)

    def setParamsFromMeshDict(self, meshDict):
        if meshDict is None:
            return

        e = meshDict.find_element(
            [
                {"type": "dictionary", "key": "maxCellSize"},
                {"type": "float|integer"},
            ]
        )["element"]
        if e is not None:
            self.maxCellSizeCRL.setText(e["value"])

        e = meshDict.find_element(
            [
                {"type": "dictionary", "key": "minCellSize"},
                {"type": "float|integer"},
            ]
        )["element"]
        if e is not None:
            self.minCellSizeCRL.setText(e["value"])

        e = meshDict.find_element(
            [
                {"type": "block", "key": "CUSTOM_OPTIONS"},
                {"type": "dictionary", "key": "featureAngle"},
                {"type": "float|integer"},
            ]
        )["element"]
        if e is not None:
            self.featureAngleCRL.setText(e["value"])

        object_names = [i[self.grid.OBJECT_NAME] for i in self.grid.table]

        for block in meshDict.find_all_elements(
            [
                {"type": "block", "key": "renameBoundary"},
                {"type": "block", "key": "newPatchNames"},
                {"type": "block"},
            ]
        ):
            block = block["element"]
            if block["key"] not in object_names:
                continue
            v = block.find_element(
                [{"type": "dictionary", "key": "type"}, {"type": "word"}]
            )["element"]["value"]
            self.grid.setCellValue(object_names.index(block["key"]), self.grid.TYPE, v)

        for block in meshDict.find_all_elements(
            [{"type": "block", "key": "localRefinement"}, {"type": "block"}]
        ):
            block = block["element"]
            if block["key"] not in object_names:
                continue
            r = block.find_element(
                [
                    {"type": "dictionary", "key": "cellSize"},
                    {"type": "float|integer"},
                ]
            )["element"]
            if r is not None:
                self.grid.setCellValue(
                    object_names.index(block["key"]),
                    self.grid.CELL_SIZE,
                    r["value"],
                )

        for block in meshDict.find_all_elements(
            [
                {"type": "block", "key": "boundaryLayers"},
                {"type": "block", "key": "patchBoundaryLayers"},
                {"type": "block"},
            ]
        ):
            block = block["element"]
            if block["key"] not in object_names:
                continue
            i = object_names.index(block["key"])
            e = block.find_element(
                [{"type": "dictionary", "key": "nLayers"}, {"type": "integer"}]
            )["element"]
            if e is not None:
                self.grid.setCellValue(i, self.grid.N_LAYERS, e["value"])
                self.grid.setCellValue(i, self.grid.BOUNDARY_LAYER, True)
            e = block.find_element(
                [
                    {"type": "dictionary", "key": "thicknessRatio"},
                    {"type": "float|integer"},
                ]
            )["element"]
            if e is not None:
                self.grid.setCellValue(i, self.grid.RATIO, e["value"])

        for block in meshDict.find_all_elements(
            [{"type": "block", "key": "objectRefinements"}, {"type": "block"}]
        ):
            block = block["element"]
            i = object_names.index(block["key"])
            e = block.find_element(
                [
                    {"type": "dictionary", "key": "cellSize"},
                    {"type": "float|integer"},
                ]
            )["element"]
            if e is not None:
                self.grid.setCellValue(i, self.grid.CELL_SIZE, e["value"])
            e = block.find_element(
                [{"type": "dictionary", "key": "type"}, {"type": "word"}]
            )["element"]
            if e is not None:
                if e["value"] == "box":
                    self.grid.setCellValue(i, self.grid.TYPE, "BoxRefine")
                elif e["value"] == "cone":
                    self.grid.setCellValue(i, self.grid.TYPE, "CylinderRefine")
                elif e["value"] == "sphere":
                    self.grid.setCellValue(i, self.grid.TYPE, "SphereRefine")

        for block in meshDict.find_all_elements(
            [{"type": "block", "key": "surfaceMeshRefinement"}, {"type": "block"}]
        ):
            block = block["element"]
            if block["key"] not in object_names:
                continue
            i = object_names.index(block["key"])
            e = block.find_element(
                [
                    {"type": "dictionary", "key": "cellSize"},
                    {"type": "float|integer"},
                ]
            )["element"]
            if e is not None:
                self.grid.setCellValue(i, self.grid.CELL_SIZE, e["value"])
                self.grid.setCellValue(i, self.grid.TYPE, "SurfaceRefine")
            e = block.find_element(
                [
                    {"type": "dictionary", "key": "refinementThickness"},
                    {"type": "float|integer"},
                ]
            )["element"]
            if e is not None:
                self.grid.setCellValue(i, self.grid.RATIO, e["value"])

    def setParamsFromSetFieldsDict(self, setFieldsDict):
        if setFieldsDict is None:
            return

        object_names = [i[self.grid.OBJECT_NAME] for i in self.grid.table]
        for block in setFieldsDict.find_all_elements(
            [
                {"type": "dictionary", "key": "regions"},
                {"type": "list"},
                {"type": "block"},
            ]
        ):
            block = block["element"]
            comment = block.find_element([{"type": "line_comment|block_comment"}])[
                "element"
            ]
            if comment is None or "freecad" not in comment["value"].lower():
                continue
            for i, obj in enumerate(object_names):
                if obj not in comment["value"]:
                    continue
                if block["key"] == "boxToCell":
                    self.grid.setCellValue(i, self.grid.TYPE, "BoxSet")
                elif block["key"] == "cylinderToCell":
                    self.grid.setCellValue(i, self.grid.TYPE, "CylinderSet")
                else:
                    self.grid.setCellValue(i, self.grid.TYPE, "SphereSet")

    def setParamsFromTopoSetDict(self, topoSetDict):
        if topoSetDict is None:
            return

        object_names = [i[self.grid.OBJECT_NAME] for i in self.grid.table]
        for block in topoSetDict.find_all_elements(
            [
                {"type": "dictionary", "key": "actions"},
                {"type": "list"},
                {"type": "block"},
            ]
        ):
            block = block["element"]
            v = (
                block.find_element(
                    [{"type": "dictionary", "key": "name"}, {"type": "word"}]
                )["element"]["value"]
                .replace("CellSet", "")
                .replace()
            )
            if v not in object_names:
                continue
            if (
                block.find_element(
                    [{"type": "dictionary", "key": "source"}, {"type": "word"}]
                )["element"]["value"]
                != "rotatedBoxToCell"
            ):
                continue
            self.grid.setCellValue(object_names.index(v), self.grid.TYPE, "BoxTopo")

    def actionOnExitButton(self):
        self.close()


class MyController:
    FEATURE_ANGLE = 30
    BASHRC_PATH_4_OPENFOAM = os.path.join(
        os.sep, "opt", "OpenFOAM", "OpenFOAM-v1906", "etc", "bashrc"
    )
    if not os.path.exists(BASHRC_PATH_4_OPENFOAM):
        BASHRC_PATH_4_OPENFOAM = os.path.join(
            os.sep, "usr", "lib", "openfoam", "openfoam2106", "etc", "bashrc"
        )
    SOLVER_PATH_TEMPLATE = os.path.join(os.sep, "opt", "DEXCS", "template", "dexcs")

    def __init__(self):
        import FreeCAD
        import Part

        self.doc = App.ActiveDocument
        self.model = MyModel()
        self.meshDict = {"": None}
        self.setFieldsDict = None
        self.topoSetDict = None
        if self.doc.FileName == "":
            QtGui.QMessageBox.critical(
                None,
                "エラー",
                "CADファイルが保存されていません．CADファイルを保存して下さい．",
                QtGui.QMessageBox.Close,
            )
            return
        for obj in self.doc.Objects:
            if (
                obj.ViewObject.Visibility
                and hasattr(obj, "Shape")
                and "PartDesign::"
                not in obj.TypeId  # Bodyや押し出しなどのフィーチャーを排除
                and not hasattr(obj, "Role")  # 軸や原点を排除
            ):
                obj.Label = obj.Label.strip()
                l = obj.Label
                obj.Label = re.sub("^([0-9])", r"_\1", l.replace(" ", "_"))
                if obj.Label != l:
                    QtGui.QMessageBox.warning(
                        None,
                        "オブジェクトラベル違反",
                        f"ラベル{l}を{obj.Label}に変更しました．",
                        QtGui.QMessageBox.Close,
                    )
        try:
            self.MeshFrame = MeshFrame(
                controller=self,
                freecad_objects=self.doc.Objects,
                case_dir_path=os.path.dirname(self.doc.FileName),  # 絶対パス
                max_cell_size=self.model.sumOfThreeEdgesOfCadObjects(self.doc.Objects)
                / 60.0,
                feature_angle=MyController.FEATURE_ANGLE,
            )
        except Exception:
            return
        self.MeshFrame.show()

    def actionOnCaseButton(self):
        dir_path = QtGui.QFileDialog.getExistingDirectory(
            self.MeshFrame,
            "Choose a directory.",
            os.path.expanduser(os.path.join("~", "Desktop")),
        )  # 絶対パス
        if dir_path != "":
            self.MeshFrame.caseDirST.setText(dir_path)

    def actionOnOpenButton(self):
        case_dir_path = self.MeshFrame.caseDirST.text()
        if os.path.isdir(case_dir_path):
            subprocess.run(["xdg-open", case_dir_path])

    def actionOnExportButton(self):
        if not os.path.isdir(self.MeshFrame.caseDirST.text()):
            QtGui.QMessageBox.critical(
                None,
                "エラー",
                f"{self.MeshFrame.caseDirST.text()}はフォルダではありません．",
                QtGui.QMessageBox.Close,
            )
            return
        case_dir_path = self.MeshFrame.caseDirST.text()  # 絶対パス
        # (DEXCS2019を参考に) OpenFOAMのケースフォルダでない場合の処理を追加（2019/9/6）
        if not os.path.isdir(os.path.join(case_dir_path, "constant")):
            subprocess.run(
                [
                    "rsync",
                    "-a",
                    os.path.join(MyController.SOLVER_PATH_TEMPLATE, "constant"),
                    case_dir_path,
                    "--exclude",
                    "polyMesh",
                ]
            )
        if not os.path.isdir(os.path.join(case_dir_path, "system")):
            shutil.copytree(
                os.path.join(MyController.SOLVER_PATH_TEMPLATE, "system"),
                os.path.join(case_dir_path, "system"),
            )
        if not os.path.isdir(os.path.join(case_dir_path, "0")):
            shutil.copytree(
                os.path.join(MyController.SOLVER_PATH_TEMPLATE, "0"),
                os.path.join(case_dir_path, "0"),
            )

        def make_files(case_dir_path, meshDict, avail_header=None, unavail_headers=[]):
            triSurface = os.path.join(case_dir_path, "constant", "triSurface")
            if os.path.isdir(triSurface):
                shutil.rmtree(triSurface)
            elif os.path.isfile(triSurface):
                os.remove(triSurface)
            os.mkdir(triSurface)
            stl_file_path = os.path.join(
                triSurface,
                re.sub("^([0-9])", r"_\1", f"{os.path.basename(case_dir_path)}.stl"),
            )
            self.model.exportStl(
                self.doc.Objects, self.MeshFrame.grid, stl_file_path, unavail_headers
            )
            fms_file_path = f"{stl_file_path[:-3]}fms"
            command = (
                f". '{MyController.BASHRC_PATH_4_OPENFOAM}' && "
                f"surfaceFeatureEdges -angle {self.MeshFrame.featureAngleCRL.text()} "
                f"{stl_file_path} {fms_file_path}"
            )
            try:
                subprocess.run(command, shell=True, check=True)
            except:
                QtGui.QMessageBox.critical(
                    None,
                    "エラー",
                    f"{command}が失敗しました．",
                    QtGui.QMessageBox.Close,
                )
                raise

            self.model.makeMeshDict(
                case_dir_path=case_dir_path,
                surface_file_path=fms_file_path,
                max_cell_size=self.MeshFrame.maxCellSizeCRL.text(),
                freecad_objects=self.doc.Objects,
                grid=self.MeshFrame.grid,
                feature_angle=self.MeshFrame.featureAngleCRL.text(),
                min_cell_size=self.MeshFrame.minCellSizeCRL.text(),
                meshDict=meshDict,
                avail_header=avail_header,
                unavail_headers=unavail_headers,
            )

        s = set()  # マルチリージョンかの判定
        for i in self.MeshFrame.grid.table:
            if i[self.MeshFrame.grid.TYPE] == "mappedWall":
                m = pat_region_boundary.match(i[self.MeshFrame.grid.OBJECT_NAME])
                if m is None:
                    QtGui.QMessageBox.critical(
                        None,
                        "mappedWallの名前の付け方",
                        "mappedWallの名前の付け方は，以下のどちらかだけが許されます：\n"
                        "  自分の領域名.to.相手の領域名    または    自分の領域名.to.相手の領域名.数字",
                        QtGui.QMessageBox.Close,
                    )
                    return
                s.update([m["region_from"], m["region_to"]])
        regions = list(s)

        try:
            if len(regions) == 0:
                make_files(case_dir_path=case_dir_path, meshDict=self.meshDict[""])
            else:
                for r in regions:
                    c = os.path.join(case_dir_path, cases_path, r)
                    os.makedirs(os.path.join(c, "constant"), exist_ok=True)
                    os.makedirs(os.path.join(c, "system"), exist_ok=True)
                    make_files(
                        case_dir_path=c,
                        meshDict=self.meshDict.get(r, None),
                        avail_header=f"{r}.",
                        unavail_headers=[f"{i}." for i in regions if i != r],
                    )
        except:
            return

        self.model.makeSetFieldsDict(
            case_dir_path=case_dir_path,
            freecad_objects=self.doc.Objects,
            grid=self.MeshFrame.grid,
            setFieldsDict=self.setFieldsDict,
        )
        self.model.makeTopoSetDict(
            case_dir_path=case_dir_path,
            freecad_objects=self.doc.Objects,
            grid=self.MeshFrame.grid,
            topoSetDict=self.topoSetDict,
        )
        QtGui.QMessageBox.information(
            None,
            "書き出し",
            "cfMeshの設定ファイルsystem/meshDictを書き出しました．",
            QtGui.QMessageBox.Close,
        )

    def actionOnCartesianMeshButton(self):
        case_dir_path = self.MeshFrame.caseDirST.text()
        if (
            QtGui.QMessageBox.question(
                None,
                "cartesianMesh",
                "メッシュ生成コマンドcartesianMeshを実行しますか？",
                QtGui.QMessageBox.Yes,
                QtGui.QMessageBox.No,
            )
            == QtGui.QMessageBox.Yes
        ):
            cwd = os.getcwd()
            os.chdir(case_dir_path)
            subprocess.run(
                [
                    "gnome-terminal",
                    "--",
                    "bash",
                    "-c",
                    f". '{MyController.BASHRC_PATH_4_OPENFOAM}' && "
                    f"'{os.path.join(binDEXCS_path, 'cartesianMeshを実行.py')}'; exec bash",
                ]
            )
            # exec bashで画面が消えなくなる
            os.chdir(cwd)

    def actionOnImproveMeshQualityButton(self):
        if (
            QtGui.QMessageBox.question(
                None,
                "improveMeshQuality",
                "メッシュ品質改良コマンドimproveMeshQualityを実行しますか？",
                QtGui.QMessageBox.Yes,
                QtGui.QMessageBox.No,
            )
            == QtGui.QMessageBox.Yes
        ):
            cwd = os.getcwd()
            os.chdir(self.MeshFrame.caseDirST.text())
            subprocess.run(
                [
                    "gnome-terminal",
                    "--",
                    "bash",
                    "-c",
                    f". '{MyController.BASHRC_PATH_4_OPENFOAM}' && "
                    f"'{os.path.join(binDEXCS_path, 'improveMeshQualityを実行.py')}'; exec bash",
                ]
            )
            # exec bashで画面が消えなくなる
            os.chdir(cwd)

    def actionOnFlattenPatchButton(self):
        if (
            QtGui.QMessageBox.question(
                None,
                "Flatten patch",
                "パッチを平面にしますか？",
                QtGui.QMessageBox.Yes,
                QtGui.QMessageBox.No,
            )
            == QtGui.QMessageBox.Yes
        ):
            cwd = os.getcwd()
            os.chdir(self.MeshFrame.caseDirST.text())
            subprocess.run(
                [
                    "gnome-terminal",
                    "--",
                    "bash",
                    "-c",
                    f". '{MyController.BASHRC_PATH_4_OPENFOAM}' && "
                    f"'{os.path.join(binDEXCS_path, 'patchを平面に.py')}'; exec bash",
                ]
            )
            # exec bashで画面が消えなくなる
            os.chdir(cwd)

    def actionOnLoadButton(self):
        case_dir_path = self.MeshFrame.caseDirST.text()  # 絶対パス

        def dictParser(dict_path):
            if not os.path.isfile(dict_path):
                return None
            d = dictParse.DictParser(file_name=dict_path)
            name = os.path.basename(dict_path)
            if (
                d.find_element(
                    [
                        {"type": "block", "key": "FoamFile"},
                        {"type": "dictionary", "key": "object"},
                        {"type": "word", "value": name},
                    ]
                )["element"]
                is None
            ):
                QtGui.QMessageBox.critical(
                    None,
                    "Error",
                    f"{d.file_name} is not a {name} file.",
                    QtGui.QMessageBox.Close,
                )
                return None
            return d

        self.MeshFrame.setAllType("N/A")

        if os.path.isdir(os.path.join(case_dir_path, cases_path)):
            for c in glob.iglob(os.path.join(case_dir_path, cases_path, f"*{os.sep}")):
                r = os.path.basename(os.path.normpath(c))
                self.meshDict[r] = dictParser(os.path.join(c, "system", "meshDict"))
                self.MeshFrame.setParamsFromMeshDict(self.meshDict[r])
        elif os.path.isdir(case_dir_path):
            self.meshDict[""] = dictParser(
                os.path.join(case_dir_path, "system", "meshDict")
            )
            self.MeshFrame.setParamsFromMeshDict(self.meshDict[""])

        self.setFieldsDict = dictParser(
            os.path.join(case_dir_path, "system", "setFieldsDict")
        )
        self.MeshFrame.setParamsFromSetFieldsDict(self.setFieldsDict)

        self.topoSetDict = dictParser(
            os.path.join(case_dir_path, "system", "topoSetDict")
        )
        self.MeshFrame.setParamsFromTopoSetDict(self.topoSetDict)

    def actionOnEditButton(self):
        meshDict_path = os.path.join(
            self.MeshFrame.caseDirST.text(), "system", "meshDict"
        )
        if not os.path.isfile(meshDict_path):
            QtGui.QMessageBox.critical(
                None,
                "ファイルエラー",
                "system/meshDictファイルがありません．",
                QtGui.QMessageBox.Close,
            )
            return
        if (
            QtGui.QMessageBox.question(
                None,
                "編集",
                "system/meshDictファイルを編集しますか？\n",
                QtGui.QMessageBox.Yes,
                QtGui.QMessageBox.No,
            )
            == QtGui.QMessageBox.Yes
        ):
            subprocess.run(["gedit", meshDict_path])


class MyModel:
    @staticmethod
    def sumOfThreeEdgesOfCadObjects(freecad_objects):
        xmin = ymin = zmin = float("inf")
        xmax = ymax = zmax = float("-inf")
        for obj in freecad_objects:
            try:
                if (
                    obj.ViewObject.Visibility
                    and hasattr(obj, "Shape")
                    and "PartDesign::"
                    not in obj.TypeId  # Bodyや押し出しなどのフィーチャーを排除
                    and not hasattr(obj, "Role")  # 軸や原点を排除
                ):
                    xmin = min(xmin, obj.Shape.BoundBox.XMin)
                    ymin = min(ymin, obj.Shape.BoundBox.YMin)
                    zmin = min(zmin, obj.Shape.BoundBox.ZMin)
                    xmax = max(xmax, obj.Shape.BoundBox.XMax)
                    ymax = max(ymax, obj.Shape.BoundBox.YMax)
                    zmax = max(zmax, obj.Shape.BoundBox.ZMax)
            except Exception:
                pass
        return xmax - xmin + ymax - ymin + zmax - zmin

    @staticmethod
    def corr_obj_name(obj_name, unavail_headers=[]):
        if any(
            obj_name.startswith(i) for i in unavail_headers
        ):  # 使わないオブジェクトに対するヘッダがついている時
            m = pat_region_boundary.match(obj_name)
            if m is None:
                return None
            obj_name = (
                f"{m['region_to']}.to.{m['region_from']}"
                f"{'' if m['number'] is None else m['number']}"
            )  # 領域境界の場合，.to.の前後を入れ替えれば使うオブジェクトになるかもしれない
            if any(obj_name.startswith(i) for i in unavail_headers):
                return None
        return obj_name

    @staticmethod
    def exportStl(freecad_objects, grid, file_path, unavail_headers=[]):
        fd, tmp_stl = tempfile.mkstemp(suffix=".ast")
        os.close(fd)
        os.remove(tmp_stl)
        xmin = ymin = zmin = float("inf")
        xmax = ymax = zmax = float("-inf")
        with open(file_path, "w") as f:
            for i in grid.table:
                if i[grid.TYPE] in (
                    "BoxRefine",
                    "CylinderRefine",
                    "SphereRefine",
                    "BoxSet",
                    "CylinderSet",
                    "SphereSet",
                    "BoxTopo",
                    "CylinderTopo",
                    "SphereTopo",
                    "N/A",
                ):
                    continue
                obj_name = MyModel.corr_obj_name(i[grid.OBJECT_NAME], unavail_headers)
                if obj_name is None:
                    continue
                obj = next(
                    (j for j in freecad_objects if i[grid.OBJECT_NAME] == j.Label), None
                )
                if i[grid.TYPE] == "SurfaceRefine":
                    file_name = os.path.join(os.path.dirname(file_path), obj_name)
                    Mesh.export([obj], f"{file_name}.ast")  # ascii format
                    os.rename(f"{file_name}.ast", f"{file_name}.stl")  # can overwrite
                else:
                    # ascii stlフォーマット
                    # solid 任意の文字列
                    # facet normal x成分値 y成分値 z成分値
                    # outer loop
                    # vertex x成分値 y成分値 z成分値
                    # vertex x成分値 y成分値 z成分値
                    # vertex x成分値 y成分値 z成分値
                    # endloop
                    # endfacet
                    # （facet normal行～endfacet行までを１枚の三角形データとして以降くり返し）
                    # ..............
                    # endsolid 任意の文字列
                    Mesh.export([obj], tmp_stl)
                    for line in open(tmp_stl, "r"):
                        if "endsolid" in line:
                            f.write(f"endsolid {obj_name}\n")
                        elif "solid" in line:
                            f.write(f"solid {obj_name}\n")
                        else:
                            f.write(line)
                            if line.lstrip().startswith("vertex"):
                                x, y, z = [float(j) for j in line.split()[1:]]
                                xmin, ymin, zmin = (
                                    min(xmin, x),
                                    min(ymin, y),
                                    min(zmin, z),
                                )
                                xmax, ymax, zmax = (
                                    max(xmax, x),
                                    max(ymax, y),
                                    max(zmax, z),
                                )
                    os.remove(tmp_stl)
        return xmin, ymin, zmin, xmax, ymax, zmax

    @staticmethod
    def makeMeshDict(
        case_dir_path,
        surface_file_path,
        max_cell_size,
        freecad_objects,
        grid,
        feature_angle,
        min_cell_size,
        meshDict,
        avail_header=None,
        unavail_headers=[],
    ):
        meshDict_path = os.path.join(case_dir_path, "system", "meshDict")
        if os.path.isfile(meshDict_path):
            shutil.copy(meshDict_path, f"{meshDict_path}_bak")
        with open(meshDict_path, "w") as f:
            f.write(
                "FoamFile\n"
                "{\n"
                "\tversion\t2.0;\n"
                "\tformat\tascii;\n"
                "\tclass\tdictionary;\n"
                '\tlocation\t"system";\n'
                "\tobject\tmeshDict;\n"
                "}\n"
                "\n"
                "// A manual is available on\n"
                "// http://cfmesh.com/wp-content/uploads/2015/09/User_Guide-cfMesh_v1.1.pdf\n"
            )

            f.write(
                "\n"
                "CUSTOM_OPTIONS\n"
                "{\n"
                f"\tfeatureAngle\t{feature_angle}; // used in surfaceFeatureEdges utility\n"
                "}\n"
            )

            e = dictParse.find_element(
                meshDict,
                [
                    {"type": "dictionary", "key": "keepCellsIntersectingBoundary"},
                    {"type": "integer"},
                ],
            )["element"]
            f.write(
                "\n"
                "// STL表面と交差するすべてのセルを保持し，小さな隙間も捉える．（デフォルト：0）\n"
                "// STL表面に望まない隙間がある時に，0にすると良い場合がある．\n"
                f"keepCellsIntersectingBoundary\t{'1' if e is None else e['value']}; "
                "// 1 active or 0 inactive\n"
            )
            e = dictParse.find_element(
                meshDict,
                [
                    {"type": "dictionary", "key": "checkForGluedMesh"},
                    {"type": "integer"},
                ],
            )["element"]
            f.write(
                "\n"
                "// メッシュ生成の最終段階で，セルが意図せず重なったり，"
                "密着しすぎたりしていないかをチェックし，修正する．（デフォルト：0）\n"
                f"checkForGluedMesh\t{'1' if e is None else e['value']}; // 1 active or 0 inactive\n"
            )

            f.write(f"\nmaxCellSize\t{max_cell_size}; // 必須\n")
            if min_cell_size == "":
                min_cell_size = dictParse.find_element(
                    meshDict,
                    [
                        {"type": "dictionary", "key": "minCellSize"},
                        {"type": "float|integer"},
                    ],
                )["element"]
                if min_cell_size is not None:
                    min_cell_size = min_cell_size["value"]
            f.write(
                f"{'// ' if min_cell_size is None else ''}minCellSize\t"
                f"{'1' if min_cell_size is None else min_cell_size}; // 必須ではない．\n"
            )

            f.write("\n")
            e = dictParse.find_element(
                meshDict,
                [
                    {"type": "dictionary", "key": "boundaryCellSize"},
                    {"type": "float|integer"},
                ],
            )["element"]
            f.write(
                f"{'// ' if e is None else ''}boundaryCellSize\t"
                f"{'0.5' if e is None else e['value']}; // 必須ではない．\n"
            )
            e = dictParse.find_element(
                meshDict,
                [
                    {
                        "type": "dictionary",
                        "key": "boundaryCellSizeRefinementThickness",
                    },
                    {"type": "float|integer"},
                ],
            )["element"]
            f.write(
                f"{'// ' if e is None else ''}boundaryCellSizeRefinementThickness\t"
                f"{'5.0' if e is None else e['value']}; // 必須ではない．\n"
            )

            f.write(
                "\n"
                f'surfaceFile\t"constant/triSurface/{os.path.basename(surface_file_path)}"; // 必須\n'
            )

            boundaryLayers = dictParse.find_element(
                meshDict, [{"type": "block", "key": "boundaryLayers"}]
            )["element"]

            f.write("\nboundaryLayers\n{\n")

            e = dictParse.find_element(
                boundaryLayers,
                [
                    {"type": "dictionary", "key": "optimiseLayer"},
                    {"type": "integer"},
                ],
            )["element"]
            f.write(
                "\t// 境界層の自動整形．デフォルトは0．\n"
                f"\toptimiseLayer\t{'1' if e is None else e['value']}; // 1 active or 0 inactive\n"
            )

            for dictionary in dictParse.find_all_elements(
                boundaryLayers,
                [{"type": "dictionary", "except key": "optimiseLayer"}],
            ):
                f.write(f"\n\t{dictionary['element'].file_string(indent_level=1)}\n")

            optimisationParameters = dictParse.find_element(
                boundaryLayers, [{"type": "block", "key": "optimisationParameters"}]
            )["element"]

            f.write("\n\toptimisationParameters\n\t{\n")

            e = dictParse.find_element(
                optimisationParameters,
                [
                    {"type": "dictionary", "key": "featureSizeFactor"},
                    {"type": "float|integer"},
                ],
            )["element"]
            f.write(
                "\t\t// パッチでのメッシュの大きさに対する境界層メッシュの厚さ\n"
                "\t\t// 曲率が強い場所での境界層厚さを制御する．デフォルトは0.3．\n"
                f"\t\tfeatureSizeFactor\t{'0.3' if e is None else e['value']};\n"
            )

            e = dictParse.find_element(
                optimisationParameters,
                [
                    {"type": "dictionary", "key": "relThicknessTol"},
                    {"type": "float|integer"},
                ],
            )["element"]
            f.write(
                "\n"
                "\t\t// 境界層メッシュ内の隣り合う2点が持つ層厚みの差を，その2点間の距離で割った値の最大許容値．必須ではない．\n"
                f"\t\trelThicknessTol\t{'0.2' if e is None else e['value']};\n"
            )
            for dictionary in dictParse.find_all_elements(
                optimisationParameters,
                [
                    {
                        "type": "dictionary",
                        "except key": "featureSizeFactor|relThicknessTol",
                    }
                ],
            ):
                f.write(f"\n\t\t{dictionary['element'].file_string(indent_level=2)}\n")

            f.write("\t}\n")  # optimisationParameters

            patchBoundaryLayers = dictParse.find_element(
                boundaryLayers, [{"type": "block", "key": "patchBoundaryLayers"}]
            )["element"]

            f.write("\n\tpatchBoundaryLayers\n\t{\n")

            for i in grid.table:
                if not i[grid.BOUNDARY_LAYER] or i[grid.TYPE] in (
                    "BoxRefine",
                    "CylinderRefine",
                    "SphereRefine",
                    "SurfaceRefine",
                    "BoxSet",
                    "CylinderSet",
                    "SphereSet",
                    "BoxTopo",
                    "CylinderTopo",
                    "SphereTopo",
                    "N/A",
                ):
                    continue
                obj_name = MyModel.corr_obj_name(i[grid.OBJECT_NAME], unavail_headers)
                if obj_name is None:
                    continue
                f.write(
                    f"\t\t{obj_name}\n"
                    "\t\t{\n"
                    f"\t\t\tnLayers\t{i[grid.N_LAYERS]}; // 必須ではない．\n"
                    f"\t\t\tthicknessRatio\t{i[grid.RATIO]};\n"
                )

                block = dictParse.find_element(
                    patchBoundaryLayers,
                    [{"type": "block", "key": obj_name}],
                )["element"]

                e = dictParse.find_element(
                    block,
                    [
                        {"type": "dictionary", "key": "maxFirstLayerThickness"},
                        {"type": "float|integer"},
                    ],
                )["element"]
                if e is None:
                    f.write("//\t\t\tmaxFirstLayerThickness\t0.5; // 必須ではない．\n")
                else:
                    f.write(
                        f"\t\t\tmaxFirstLayerThickness\t{e['value']}; // 必須ではない．\n"
                    )

                e = dictParse.find_element(
                    block,
                    [
                        {"type": "dictionary", "key": "allowDiscontinuity"},
                        {"type": "integer"},
                    ],
                )["element"]
                f.write(
                    f"\t\t\tallowDiscontinuity\t{'0' if e is None else e['value']}; "
                    "// 1 active or 0 inactive\n"
                )
                f.write("\t\t}\n")

            f.write(
                "\t}\n"  # patchBoundaryLayers
                "}\n"
            )  # boundaryLayers

            f.write(
                "\n"
                "// keepCellsIntersectingBoundaryが1の時に有効．必須ではない．\n"
                "keepCellsIntersectingPatches\n"
                "{\n"
                '//\t"patch.*" // accepts regex\n'
                "//\t{\n"
                "//\t\tkeepCells\t1; // 1 active or 0 inactive\n"
                "//\t}\n"
                "}\n"
                "\n"
                "// keepCellsIntersectingBoundaryが1の時に有効．必須ではない．\n"
                "removeCellsIntersectingPatches\n"
                "{\n"
                '//\t"patch.*" // accepts regex\n'
                "//\t{\n"
                "//\t\tkeepCells\t0; // 0 remove or 1 keep\n"
                "//\t}\n"
                "}\n"
            )

            f.write("\nlocalRefinement\n{\n")
            for i in grid.table:
                if i[grid.CELL_SIZE] == "" or i[grid.TYPE] in (
                    "BoxRefine",
                    "CylinderRefine",
                    "SphereRefine",
                    "SurfaceRefine",
                    "BoxSet",
                    "CylinderSet",
                    "SphereSet",
                    "BoxTopo",
                    "CylinderTopo",
                    "SphereTopo",
                    "N/A",
                ):
                    continue
                obj_name = MyModel.corr_obj_name(i[grid.OBJECT_NAME], unavail_headers)
                if obj_name is None:
                    continue
                ref_thickness = i[grid.CELL_SIZE]
                ref_level = 0
                ref_value = float(max_cell_size) / ref_thickness
                while ref_value > 1.0:
                    ref_level += 1
                    ref_value *= 0.5
                f.write(
                    f"\t{obj_name}\n"
                    "\t{\n"
                    f"\t\tcellSize\t{ref_thickness};\n"
                    f"//\t\tadditionalRefinementLevels\t{ref_level}; // Relative to the maximum cell size\n"
                    f"//\t\trefinementThickness\t{5 * ref_thickness};\n"
                    "\t}\n"
                    "\n"
                )
            f.write(
                '//\t"patch.*" // accepts regex\n'
                "//\t{\n"
                "//\t\tcellSize 1;\n"
                "//\t\tadditionalRefinementLevels\t1;\n"
                "//\t\trefinementThickness\t1.2;\n"
                "//\t}\n"
                "}\n"
            )  # localRefinement

            object_names = [i[grid.OBJECT_NAME] for i in grid.table]
            f.write("\nobjectRefinements\n{")
            for i in grid.table:
                if i[grid.CELL_SIZE] == "" or i[grid.TYPE] not in (
                    "BoxRefine",
                    "CylinderRefine",
                    "SphereRefine",
                ):
                    continue
                obj_name = MyModel.corr_obj_name(i[grid.OBJECT_NAME], unavail_headers)
                if obj_name is None:
                    continue
                obj = next(
                    (j for j in freecad_objects if i[grid.OBJECT_NAME] == j.Label),
                    None,
                )
                ref_thickness = i[grid.CELL_SIZE]
                ref_level = 0
                ref_value = float(max_cell_size) / ref_thickness
                while ref_value > 1.0:
                    ref_level += 1
                    ref_value *= 0.5
                f.write(f"\n\t{obj_name}\n\t{{\n")
                if i[grid.TYPE] == "BoxRefine":
                    c = obj.Shape.CenterOfMass
                    f.write(
                        "\t\ttype\tbox;\n"
                        f"\t\tcellSize\t{ref_thickness};\n"
                        f"//\t\tadditionalRefinementLevels\t{ref_level}; // Relative to the maximum cell size\n"
                        f"\t\tcentre\t({c.x} {c.y} {c.z});\n"
                        f"\t\tlengthX\t{obj.Length.Value};\n"
                        f"\t\tlengthY\t{obj.Width.Value};\n"
                        f"\t\tlengthZ\t{obj.Height.Value};\n"
                    )
                elif i[grid.TYPE] == "CylinderRefine":
                    b = obj.Placement.Base
                    m = obj.Placement.Matrix
                    h = obj.Height.Value
                    f.write(
                        "\t\ttype\tcone;\n"
                        f"\t\tcellSize\t{ref_thickness};\n"
                        f"//\t\tadditionalRefinementLevels\t{ref_level}; "
                        "// Relative to the maximum cell size\n"
                        f"\t\tp0\t({b.x} {b.y} {b.z});\n"
                        f"\t\tp1\t({b.x + m.A13 * h} {b.y + m.A23 * h} {b.z + m.A33 * h});\n"
                        f"\t\tradius0\t{obj.Radius.Value};\n"
                        f"\t\tradius1\t{obj.Radius.Value};\n"
                    )
                elif i[grid.TYPE] == "SphereRefine":
                    b = obj.Placement.Base
                    f.write(
                        "\t\ttype\tsphere;\n"
                        f"\t\tcellSize\t{ref_thickness};\n"
                        f"//\t\tadditionalRefinementLevels\t{ref_level}; "
                        "// Relative to the maximum cell size\n"
                        f"\t\tcentre\t({b.x} {b.y} {b.z});\n"
                        f"\t\tradius\t{obj.Radius.Value};\n"
                        f"\t\trefinementThickness\t{obj.Radius.Value};\n"
                    )
                f.write("\t}\n")
            for block in dictParse.find_all_elements(
                meshDict,
                [{"type": "block", "key": "objectRefinements"}, {"type": "block"}],
            ):
                block = block["element"]
                if block["key"] not in object_names:
                    f.write(f"\n\t{block.file_string(indent_level=1)}\n")
            f.write(
                "\n"
                "//\tboxExample\n"
                "//\t{\n"
                "//\t\ttype\tbox;\n"
                "//\t\tcellSize\t7.51;\n"
                "//\t\tcentre\t(500 500 150);\n"
                "//\t\tlengthX\t100;\n"
                "//\t\tlengthY\t150;\n"
                "//\t\tlengthZ\t200;\n"
                "//\t}\n"
                "\n"
                "//\tconeExample\n"
                "//\t{\n"
                "//\t\ttype\tcone;\n"
                "//\t\tcellSize\t7.51;\n"
                "//\t\tp0\t(-100 1873 -320);\n"
                "//\t\tp1\t(-560 1400 0);\n"
                "//\t\tradius0\t200;\n"
                "//\t\tradius1\t300;\n"
                "//\t}\n"
                "\n"
                "//\thollowConeExample\n"
                "//\t{\n"
                "//\t\ttype\thollowCone;\n"
                "//\t\tadditionalRefinementLevels\t2; // Relative to the maximum cell size\n"
                "//\t\tp0\t(-100 1873 -320);\n"
                "//\t\tp1\t(-560 1400 0);\n"
                "//\t\tradius0_Inner\t200;\n"
                "//\t\tradius0_Outer\t300;\n"
                "//\t\tradius1_Inner\t200;\n"
                "//\t\tradius1_Outer\t300;\n"
                "//\t}\n"
                "\n"
                "//\tsphereExample\n"
                "//\t{\n"
                "//\t\ttype\tsphere;\n"
                "//\t\tcellSize\t7.51;\n"
                "//\t\tcentre\t(0 700 0);\n"
                "//\t\tradius\t50;\n"
                "//\t\trefinementThickness\t50;\n"
                "//\t}\n"
                "\n"
                "//\tlineExample\n"
                "//\t{\n"
                "//\t\ttype\tline;\n"
                "//\t\tcellSize\t7.51;\n"
                "//\t\tp0\t(-750 1000 450);\n"
                "//\t\tp1\t(-750 1500 450);\n"
                "//\t\trefinementThickness\t40;\n"
                "//\t}\n"
                "}\n"
            )  # objectRefinements

            f.write("\nsurfaceMeshRefinement\n{")
            for i in grid.table:
                if (
                    i[grid.CELL_SIZE] != ""
                    and i[grid.TYPE] == "SurfaceRefine"
                    and not any(
                        i[grid.OBJECT_NAME].startswith(j) for j in unavail_headers
                    )
                ):
                    ref_thickness = i[grid.CELL_SIZE]
                    ref_level = 0
                    ref_value = float(max_cell_size) / ref_thickness
                    while ref_value > 1.0:
                        ref_level += 1
                        ref_value *= 0.5
                    f.write(
                        "\n"
                        f"\t{i[grid.OBJECT_NAME]}\n"
                        "\t{\n"
                        f'\t\tsurfaceFile\t"constant/triSurface/{i[grid.OBJECT_NAME]}.stl";\n'
                        f"\t\tcellSize\t{ref_thickness};\n"
                        f"//\t\tadditionalRefinementLevels\t{ref_level}; "
                        "// Relative to the maximum cell size\n"
                        f"\t\trefinementThickness\t{i[grid.RATIO]};\n"
                        "\t}\n"
                    )
            for block in dictParse.find_all_elements(
                meshDict,
                [
                    {"type": "block", "key": "surfaceMeshRefinement"},
                    {"type": "block"},
                ],
            ):
                block = block["element"]
                if block["key"] not in object_names:
                    f.write(f"\n\t{block.file_string(indent_level=1)}\n")
            f.write("}\n")

            f.write(
                "\n"
                "anisotropicSources // 非等方セルの設定\n"
                "{\n"
                "//\tboxExample\n"
                "//\t{\n"
                "//\t\ttype\tbox;\n"
                "//\t\tcentre\t(0 0 0);\n"
                "//\t\tlengthX\t1000;\n"
                "//\t\tlengthY\t1000;\n"
                "//\t\tlengthZ\t200;\n"
                "//\t\tscaleX\t1; // x方向の倍率．1より大きいと粗くなり，小さいと細かくなる．\n"
                "//\t\tscaleY\t1; // y方向の倍率．1より大きいと粗くなり，小さいと細かくなる．\n"
                "//\t\tscaleZ\t0.3; // z方向の倍率．1より大きいと粗くなり，小さいと細かくなる．\n"
                "//\t}\n"
                "\n"
                "//\tplaneExample\n"
                "//\t{\n"
                "//\t\ttype\tplane;\n"
                "//\t\tnormal\t(0 0 1);\n"
                "//\t\torigin\t(0 0 250);\n"
                "//\t\tscalingDistance\t125; // normal方向にscalingDistanceまでを非等方にする．\n"
                "//\t\tscalingFactor\t0.5; // normal方向の倍率．1より大きいと粗くなり，小さいと細かくなる．\n"
                "//\t}\n"
                "}\n"
            )

            f.write("\nrenameBoundary\n{\n\tnewPatchNames\n\t{\n")
            for i in grid.table:
                if i[grid.TYPE] in (
                    "BoxRefine",
                    "CylinderRefine",
                    "SphereRefine",
                    "SurfaceRefine",
                    "BoxSet",
                    "CylinderSet",
                    "SphereSet",
                    "BoxTopo",
                    "CylinderTopo",
                    "SphereTopo",
                    "N/A",
                ):
                    continue
                obj_name = i[grid.OBJECT_NAME]
                if any(obj_name.startswith(j) for j in unavail_headers):
                    m = pat_region_boundary.match(obj_name)
                    if m is None:
                        continue
                    obj_name = (
                        f"{m['region_to']}.to.{m['region_from']}"
                        f"{'' if m['number'] is None else m['number']}"
                    )
                    if any(obj_name.startswith(j) for j in unavail_headers):
                        continue
                new_name = (
                    obj_name[len(avail_header) :]
                    if i[grid.TYPE] != "mappedWall"
                    and avail_header is not None
                    and obj_name.startswith(avail_header)
                    else obj_name
                )
                f.write(
                    f"\t\t{obj_name}\n"
                    "\t\t{\n"
                    f"\t\t\tnewName\t{new_name};\n"
                    f"\t\t\ttype\t{i[grid.TYPE]};\n"
                    "\t\t}\n"
                )
            f.write(
                "\t}\n"  # newPatchNames
                "}\n"
            )  # renameBoundary

            for element in dictParse.find_all_elements(
                meshDict,
                [
                    {
                        "type": "block|dictionary",
                        "except key": (
                            "FoamFile"
                            "|"
                            "CUSTOM_OPTIONS"
                            "|"
                            "keepCellsIntersectingBoundary"
                            "|"
                            "checkForGluedMesh"
                            "|"
                            "maxCellSize"
                            "|"
                            "boundaryCellSize"
                            "|"
                            "boundaryCellSizeRefinementThickness"
                            "|"
                            "minCellSize"
                            "|"
                            "surfaceFile"
                            "|"
                            "boundaryLayers"
                            "|"
                            "keepCellsIntersectingPatches"
                            "|"
                            "removeCellsIntersectingPatches"
                            "|"
                            "localRefinement"
                            "|"
                            "objectRefinements"
                            "|"
                            "surfaceMeshRefinement"
                            "|"
                            "anisotropicSources"
                            "|"
                            "renameBoundary"
                        ),
                    }
                ],
            ):
                f.write(f"\n{element['element'].file_string()}\n")

        os.chmod(meshDict_path, 0o0666)

        controlDict_path = os.path.join(case_dir_path, "system", "controlDict")
        if not os.path.isfile(
            controlDict_path
        ):  # controlDictがないとcartesianMeshが動かない
            with open(controlDict_path, "w") as f:
                f.write(
                    "FoamFile\n"
                    "{\n"
                    "\tversion\t2.0;\n"
                    "\tformat\tascii;\n"
                    "\tclass\tdictionary;\n"
                    '\tlocation\t"system";\n'
                    "\tobject\tcontrolDict;\n"
                    "}\n"
                    "deltaT\t1;\n"
                    "writeControl\ttimeStep;\n"
                    "writeInterval\t1;\n"
                )
        os.chmod(controlDict_path, 0o0666)

    @staticmethod
    def makeSetFieldsDict(case_dir_path, freecad_objects, grid, setFieldsDict):
        if not any(
            (i[grid.TYPE] in ("BoxSet", "CylinderSet", "SphereSet") for i in grid.table)
        ):
            return
        dict_path = os.path.join(case_dir_path, "system", "setFieldsDict")
        if os.path.isfile(dict_path):
            shutil.copy(dict_path, f"{dict_path}_bak")

        with open(dict_path, "w") as f:
            f.write(
                "FoamFile\n"
                "{\n"
                "\tversion\t2.0;\n"
                "\tformat\tascii;\n"
                "\tclass\tdictionary;\n"
                '\tlocation\t"system";\n'
                "\tobject\tsetFieldsDict;\n"
                "}\n"
                "\n"
            )

            defaultFieldValues = dictParse.find_element(
                setFieldsDict, [{"type": "dictionary", "key": "defaultFieldValues"}]
            )["element"]
            if defaultFieldValues is not None:
                f.write(f"{defaultFieldValues.file_string()}\n")
            else:
                f.write(
                    "defaultFieldValues // regionsで指定しない領域における値\n"
                    "(\n"
                    "\tvolScalarFieldValue\talpha.water 0 // ←自分の目的に合わせて書き換える\n"
                    "\tvolVectorFieldValue\tU ( 0 0 0 ) // ←自分の目的に合わせて書き換える\n"
                    ");\n"
                )

            regions = dictParse.find_element(
                setFieldsDict,
                [{"type": "dictionary", "key": "regions"}, {"type": "list"}],
            )["element"]
            f.write("\nregions\n(\n")
            for i in grid.table:
                if i[grid.TYPE] not in ("BoxSet", "CylinderSet", "SphereSet"):
                    continue
                obj = next(
                    (j for j in freecad_objects if i[grid.OBJECT_NAME] == j.Label), None
                )
                if i[grid.TYPE] == "BoxSet":
                    b = obj.Shape.BoundBox
                    f.write(
                        f"\tboxToCell // Object {i[grid.OBJECT_NAME]} in FreeCAD\n"
                        "\t{\n"
                        f"\t\tbox\t({0.001 * b.XMin} {0.001 * b.YMin} {0.001 * b.ZMin}) "
                        f"({0.001 * b.XMax} {0.001 * b.YMax} {0.001 * b.ZMax});\n"
                    )
                elif i[grid.TYPE] == "CylinderSet":
                    b = obj.Placement.Base
                    m = obj.Placement.Matrix
                    h = obj.Height.Value
                    f.write(
                        f"\tcylinderToCell // Object {i[grid.OBJECT_NAME]} in FreeCAD\n"
                        "\t{\n"
                        f"\t\tp1\t({0.001 * b.x} {0.001 * b.y} {0.001 * b.z});\n"
                        f"\t\tp2\t({0.001 * (b.x + m.A13 * h)} {0.001 * (b.y + m.A23 * h)} {0.001 * (b.z + m.A33 * h)});\n"
                        f"\t\tradius\t{0.001 * obj.Radius.Value};\n"
                    )
                else:  # SphereSet
                    b = obj.Placement.Base
                    f.write(
                        f"\tsphereToCell // Object {i[grid.OBJECT_NAME]} in FreeCAD\n"
                        "\t{\n"
                        f"\t\tcentre\t({0.001 * b.x} {0.001 * b.y} {0.001 * b.z});\n"
                        f"\t\tradius\t{0.001 * obj.Radius.Value};\n"
                    )
                for comment in dictParse.find_all_elements(
                    regions, [{"type": "block"}, {"type": "line_comment|block_comment"}]
                ):
                    if i[grid.OBJECT_NAME] not in comment["element"]["value"]:
                        continue
                    fieldValues = dictParse.find_element(
                        comment["parent"],
                        [{"type": "dictionary", "key": "fieldValues"}],
                    )["element"]
                    if fieldValues is None:
                        f.write(
                            "\t\tfieldValues\n"
                            "\t\t(\n"
                            "\t\t\tvolScalarFieldValue alpha.water 1 // ←自分の目的に合わせて書き換える\n"
                            "\t\t);\n"
                        )
                    else:
                        f.write(f"\t\t{fieldValues.file_string(indent_level=2)}\n")
                f.write("\t}\n")  # boxToCell, cylinderToCell, sphereToCell
            for block in dictParse.find_all_elements(regions, [{"type": "block"}]):
                block = block["element"]
                comment = dictParse.find_element(
                    block, [{"type": "line_comment|block_comment"}]
                )["element"]["value"]
                if "freecad" not in comment.lower():
                    f.write(f"\n\t{block.file_string(indent_level=1)}\n")
                f.write(");\n")  # regions

            for element in dictParse.find_all_elements(
                setFieldsDict,
                [
                    {
                        "type": "block|dictionary",
                        "except key": "FoamFile|defaultFieldValues|regions",
                    }
                ],
            ):
                f.write(f"\n{element['element'].file_string()}\n")

        os.chmod(dict_path, 0o0666)

    @staticmethod
    def makeTopoSetDict(case_dir_path, freecad_objects, grid, topoSetDict):
        if not any((i[grid.TYPE] == "BoxTopo" for i in grid.table)):
            return
        dict_path = os.path.join(case_dir_path, "system", "topoSetDict")
        if os.path.isfile(dict_path):
            shutil.copy(dict_path, f"{dict_path}_bak")

        with open(dict_path, "w") as f:
            f.write(
                "FoamFile\n"
                "{\n"
                "\tversion\t2.0;\n"
                "\tformat\tascii;\n"
                "\tclass\tdictionary;\n"
                '\tlocation\t"system";\n'
                "\tobject\ttopoSetDict;\n"
                "}\n"
            )  # FoamFile

            actions = dictParse.DictParser.find_all_element_static(
                [
                    {"type": "dictionary", "key": "actions"},
                    {"type": "list"},
                    {"type": "block"},
                ],
                parent=topoSetDict,
            )
            f.write("\nactions\n(\n")
            for i in grid.table:
                if i[grid.TYPE] not in ("BoxTopo", "CylinderTopo", "SphereTopo"):
                    continue
                block = next(
                    (
                        i["element"]
                        for i in actions
                        if dictParse.find_element(
                            i["element"],
                            [
                                {"type": "dictionary", "key": "name"},
                                {
                                    "type": "word",
                                    "value": f"{i[grid.OBJECT_NAME]}CellSet",
                                },
                            ],
                        )["element"]
                        is not None
                    ),
                    None,
                )
                if block is None:
                    action = "new"
                else:
                    action = dictParse.find_element(
                        block,
                        [{"type": "dictionary", "key": "action"}, {"type": "word"}],
                    )["element"]
                    if action is None:
                        action = "new"
                f.write(
                    "\t{"
                    f" // Object {i[grid.OBJECT_NAME]} in FreeCAD\n"
                    f"\t\tname\t{i[grid.OBJECT_NAME]}CellSet;\n"
                    "\t\ttype\tcellSet;\n"
                    f"\t\taction\t{action};\t// new | add | subtract\n"
                )
                obj = next(
                    (j for j in freecad_objects if i[grid.OBJECT_NAME] == j.Label), None
                )
                if i[grid.TYPE] == "BoxTopo":
                    b = obj.Placement.Base
                    m = obj.Placement.Matrix
                    l = obj.Length.Value
                    w = obj.Width.Value
                    h = obj.Height.Value
                    f.write(
                        "\t\tsource\trotatedBoxToCell;\n"
                        f"\t\torigin\t({0.001 * b.x} {0.001 * b.y} {0.001 * b.z});\n"
                        f"\t\ti\t({0.001 * l * m.A11} {0.001 * l * m.A21} {0.001 * l * m.A31});\n"
                        f"\t\tj\t({0.001 * w * m.A12} {0.001 * w * m.A22} {0.001 * w * m.A32});\n"
                        f"\t\tk\t({0.001 * h * m.A13} {0.001 * h * m.A23} {0.001 * h * m.A33});\n"
                    )
                elif i[grid.TYPE] == "CylinderTopo":
                    b = obj.Placement.Base
                    m = obj.Placement.Matrix
                    h = obj.Height.Value
                    f.write(
                        "\t\tsource\tcylinderToCell;\n"
                        f"\t\tp1\t({0.001 * b.x} {0.001 * b.y} {0.001 * b.z});\n"
                        f"\t\tp2\t({0.001 * (b.x + m.A13 * h)} {0.001 * (b.y + m.A23 * h)} {0.001 * (b.z + m.A33 * h)});\n"
                        f"\t\tradius\t{0.001 * obj.Radius.Value};\n"
                    )
                else:  # SphereTopo
                    b = obj.Placement.Base
                    f.write(
                        "\t\tsource\tsphereToCell;\n"
                        f"\t\torigin\t({0.001 * b.x} {0.001 * b.y} {0.001 * b.z});\n"
                        f"\t\tradius\t{0.001 * obj.Radius.Value};\n"
                    )
                f.write("\t}\n")
            for i in grid.table:
                if i[grid.TYPE] in ("BoxTopo", "CylinderTopo", "SphereTopo"):
                    f.write(
                        "\t{"
                        f" // Object {i[grid.OBJECT_NAME]} in FreeCAD\n"
                        f"\t\tname\t{i[grid.OBJECT_NAME]};\n"
                        "\t\ttype\tcellZoneSet;\n"
                        "\t\taction\tnew;\n"
                        "\t\tsource\tsetToCellZone;\n"
                        f"\t\tset\t{i[grid.OBJECT_NAME]}CellSet;\n"
                        "\t}\n"
                    )
            written_action_names = "|".join(
                [
                    f"{i[grid.OBJECT_NAME]}|{i[grid.OBJECT_NAME]}CellSet"
                    for i in grid.table
                ]
            )
            for block in actions:
                block = ["element"]
                if (
                    dictParse.find_element(
                        block,
                        [
                            {"type": "dictionary", "key": "name"},
                            {"type": "word", "except value": written_action_names},
                        ],
                    )["element"]
                    is not None
                ):
                    f.write(f"\n\t{block.file_string(indent_level=1)}\n")
            f.write(");\n")  # actions

            for element in dictParse.find_all_elements(
                topoSetDict,
                [{"type": "block|dictionary", "except key": "FoamFile|actions"}],
            ):
                f.write(f"\n{element['element'].file_string()}\n")

        os.chmod(dict_path, 0o0666)


if __name__ == "__main__":
    MyController()
